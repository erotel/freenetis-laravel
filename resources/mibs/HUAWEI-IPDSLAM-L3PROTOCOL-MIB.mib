-- ============================================================================
-- Copyright (C) 2010 by  HUAWEI TECHNOLOGIES. All rights reserved.
-- Description:  The mib used for The Protocol 802.1p priority table. Each row
--               in the table represents a different vlan with different 802.1p
--               prioriy of protocol packets configured.
-- Reference:
-- Version:      V1.08
--
-- ============================================================================
    HUAWEI-IPDSLAM-L3PROTOCOL-MIB DEFINITIONS ::= BEGIN

        IMPORTS
            huaweiUtility
                FROM HUAWEI-MIB
            OBJECT-TYPE, MODULE-IDENTITY, Integer32
                FROM SNMPv2-SMI
            hwVlanMngObject, hwVlanIndex
                FROM HUAWEI-VLAN-MIB
            hwFrameIndex, hwSlotIndex
                FROM HUAWEI-DEVICE-MIB;
                
        hwL3Protocol MODULE-IDENTITY
            LAST-UPDATED "201011200000Z"
        ORGANIZATION 
            "Huawei Technologies Co.,Ltd."
        CONTACT-INFO 
            "Huawei Industrial Base
             Bantian, Longgang
             Shenzhen 518129
             People's Republic of China 
             Website: http://www.huawei.com
             Email: support@huawei.com
            "     
            DESCRIPTION
                "The mib used for The Protocol 802.1p priority table. Each row
                 in the table represents a different vlan with different 802.1p
                 prioriy of protocol packets configured.
                "

           -- Revision history
           REVISION     "201210160000Z"
           DESCRIPTION  "V1.08, added hwUpLinkBoardModeTable and hwRouterMode."

           REVISION     "201011200000Z"
           DESCRIPTION  "V1.07, modified description of hwIPPrecedenceTable."
           
           REVISION     "201007150000Z"
           DESCRIPTION  "V1.06, modified description."

           REVISION     "201004250000Z"
           DESCRIPTION  "V1.05, modified description."

           REVISION     "201004150000Z"
           DESCRIPTION  "V1.04, modified format of this file."

           REVISION     "201002260000Z"
           DESCRIPTION  "V1.03, added hwIPPrecedenceTable."

           REVISION     "200809110000Z"
           DESCRIPTION  "V1.02, added hwProtocolDot1pPriority for MxU V800R306C01."

           REVISION     "200805110900Z"
           DESCRIPTION  "V1.01, added hwProtocolDot1pValue for MxU V800R306C01."

           REVISION    "200801150900Z"
           DESCRIPTION " V1.00, first draft."
            ::= { huaweiUtility 125 }

        hwL3ProtocolMibObject OBJECT IDENTIFIER ::= { hwL3Protocol 1 }

        hwProtocolDot1p OBJECT IDENTIFIER ::= { hwL3ProtocolMibObject 1 }

        hwProtocolDot1pTable OBJECT-TYPE
            SYNTAX SEQUENCE OF HwProtocolDot1pEntry
            MAX-ACCESS not-accessible
            STATUS current
            DESCRIPTION
               "The Protocol 802.1p priority table. Each row in the table
                represents a different vlan with different 802.1p priority of
                protocol packets configured.
                The index of this table is hwVlanIndex.
               "
            ::= { hwProtocolDot1p 1 }

        hwProtocolDot1pEntry OBJECT-TYPE
            SYNTAX HwProtocolDot1pEntry
            MAX-ACCESS not-accessible
            STATUS current
            DESCRIPTION
               "The Protocol 802.1p priority table. Each row in the table
                represents a different vlan with different 802.1p priority of
                protocol packets configured.
                The index of this entry is hwVlanIndex.
               "
            INDEX { hwVlanIndex }
            ::= { hwProtocolDot1pTable 1 }

        HwProtocolDot1pEntry ::=
            SEQUENCE {
                hwOspfDot1pPriority
                    Integer32,
                hwRipDot1pPriority
                    Integer32,
                hwLdpDot1pPriority
                    Integer32,
                hwRsvpTeDot1pPriority
                    Integer32,
                hwSnmpDot1pPriority
                    Integer32,
                hwProtocolDot1pPriority
                    Integer32
                     }

         hwOspfDot1pPriority OBJECT-TYPE
            SYNTAX Integer32 ( 0..7 )
            MAX-ACCESS read-write
            STATUS current
            DESCRIPTION
               "The 802.1p priority of OSPF protocol on this VLAN."
            DEFVAL { 0 }
            ::= { hwProtocolDot1pEntry 1 }

        hwRipDot1pPriority OBJECT-TYPE
            SYNTAX Integer32 ( 0..7 )
            MAX-ACCESS read-write
            STATUS current
            DESCRIPTION
               "The 802.1p priority of RIP protocol on this VLAN."
            DEFVAL { 0 }
            ::= { hwProtocolDot1pEntry 2 }

         hwLdpDot1pPriority OBJECT-TYPE
            SYNTAX Integer32 ( 0..7 )
            MAX-ACCESS read-write
            STATUS current
            DESCRIPTION
               "The 802.1p priority of LDP protocol on this VLAN."
            DEFVAL { 0 }
            ::= { hwProtocolDot1pEntry 3 }

        hwRsvpTeDot1pPriority OBJECT-TYPE
            SYNTAX Integer32 ( 0..7 )
            MAX-ACCESS read-write
            STATUS current
            DESCRIPTION
               "The 802.1p priority of RSVP-TE protocol on this VLAN."
            DEFVAL { 0 }
            ::= { hwProtocolDot1pEntry 4 }

         hwSnmpDot1pPriority OBJECT-TYPE
            SYNTAX Integer32 ( 0..7 )
            MAX-ACCESS read-write
            STATUS current
            DESCRIPTION
               "The 802.1p priority of SNMP protocol on this VLAN."
            DEFVAL { 0 }
            ::= { hwProtocolDot1pEntry 5 }

         hwProtocolDot1pPriority OBJECT-TYPE
            SYNTAX Integer32 ( -1..7 )
            MAX-ACCESS read-write
            STATUS current
            DESCRIPTION
               "Indicates the VLAN-based 802.1p priority of packet.
                Range: -1 - 7
                The larger the value, the higher the priority.
                The invalid value -1 is returned when this leaf is not specified.
                The meaning of each value is as follows:
                best-effort: Best-effort priority(0)
                background: Background priority(1)
                spare: Spare priority(2)
                excellent-effort: Excellent-effort priority(3)
                controlled-load: Controlled-load priority(4)
                video: Video priority(5)
                voice: Voice priority(6)
                network-management: Network-management priority(7)
               "
            DEFVAL { -1 }
            ::= { hwProtocolDot1pEntry 6 }

        hwIPPrecedence OBJECT IDENTIFIER ::= { hwL3ProtocolMibObject 2 }

        hwIPPrecedenceTable OBJECT-TYPE
            SYNTAX SEQUENCE OF HwIPPrecedenceEntry
            MAX-ACCESS not-accessible
            STATUS current
            DESCRIPTION
               "Indicates the IP protocol precedence. Each row in the table
                represents a different vlan with DSCP value of protocol
                packets configured.
                The index of this table is hwVlanIndex.
               "
            ::= { hwIPPrecedence 1 }

        hwIPPrecedenceEntry OBJECT-TYPE
            SYNTAX HwIPPrecedenceEntry
            MAX-ACCESS not-accessible
            STATUS current
            DESCRIPTION
               "Indicates the IP protocol precedence. Each row in the table
                represents a different vlan with DSCP value of protocol
                packets configured.
                The index of this entry is hwVlanIndex.
               "
            INDEX { hwVlanIndex }
            ::= { hwIPPrecedenceTable 1 }

        HwIPPrecedenceEntry ::=
            SEQUENCE {
                hwDscpValue
                    Integer32
                     }

         hwDscpValue OBJECT-TYPE
            SYNTAX Integer32 ( -1..63 )
            MAX-ACCESS read-write
            STATUS current
            DESCRIPTION
               "The DSCP value of IP protocol on this VLAN."
            DEFVAL { -1 }
            ::= { hwIPPrecedenceEntry 1 }

        hwL3FwdMode OBJECT IDENTIFIER ::= { hwL3Protocol 2 }

        hwUpLinkBoardModeTable OBJECT-TYPE
            SYNTAX SEQUENCE OF HwUpLinkBoardModeEntry
            MAX-ACCESS not-accessible
            STATUS current
            DESCRIPTION
               "Indicates the forwarding mode of the spuf board.
                The index of this table is hwFrameIndex and hwSlotIndex.
               "
            ::= { hwL3FwdMode 1 }

        hwUpLinkBoardModeEntry OBJECT-TYPE
            SYNTAX HwUpLinkBoardModeEntry
            MAX-ACCESS not-accessible
            STATUS current
            DESCRIPTION
               "Indicates the forwarding mode of the spuf board.
                The index of this table is hwFrameIndex and hwSlotIndex.
               "
            INDEX { hwFrameIndex, hwSlotIndex }
            ::= { hwUpLinkBoardModeTable 1 }

        HwUpLinkBoardModeEntry ::=
            SEQUENCE {
                hwUpLinkBoardMode
                    INTEGER
                     }

        hwUpLinkBoardMode OBJECT-TYPE
            SYNTAX INTEGER
                {
                l2mode(1),
                l3mode(2)
                }
            MAX-ACCESS read-only
            STATUS current
            DESCRIPTION
               "The fowarding mode of the spuf board.
                Options:
                1: L2 fowarding mode(1) 
                2: L3 fowarding mode(2)
               "
            ::= { hwUpLinkBoardModeEntry 1 }

       hwRouterMode OBJECT-TYPE
           SYNTAX INTEGER 
               {
               basicmode(1),
               enhancedmode(2)
               }
           MAX-ACCESS read-only
           STATUS current
	   DESCRIPTION
               "The fowarding mode of system.The default value is basic fowarding mode.
                Options:
                1: Basic fowarding mode(1) 
                2: Enhanced fowarding mode(2)
               "	       
	   ::= { hwL3FwdMode 2 }
	   
       END
