-- ============================================================================
-- Copyright (C) 2010 by  HUAWEI TECHNOLOGIES. All rights reserved.
-- Description:  This mib file is used for Manage the static route table configuration.
-- Reference:  
-- Version:      V1.2
-- 
-- ============================================================================

    HUAWEI-RM-EXT-MIB DEFINITIONS ::= BEGIN

        IMPORTS
            hwDatacomm            
                FROM HUAWEI-MIB            
            OBJECT-GROUP, MODULE-COMPLIANCE, NOTIFICATION-GROUP            
                FROM SNMPv2-CONF            
            IpAddress, Integer32, Unsigned32, OBJECT-TYPE, MODULE-IDENTITY, 
            NOTIFICATION-TYPE            
                FROM SNMPv2-SMI            
            RowStatus            
                FROM SNMPv2-TC;
    
        hwRmExt MODULE-IDENTITY 
            LAST-UPDATED "201011250000Z"
            ORGANIZATION 
                "Huawei Technologies co.,Ltd"
            CONTACT-INFO 
                "Huawei Industrial Base
                Bantian, Longgang
                Shenzhen 518129
                People's Republic of China
                Website: http://www.huawei.com
                Email: support@huawei.com"
            DESCRIPTION 
                "This mib file is used for Manage the static route table configuration."
            -- Revision history
            REVISION "201011250000Z"
            DESCRIPTION 
                "V1.2, updated the description." 
                
            REVISION "201008200000Z"
            DESCRIPTION 
                "V1.1, modify format of enumerations and description."

            REVISION "200811100000Z"
            DESCRIPTION 
                "V1.0, the first draft."
            ::= { hwDatacomm 145 }
        
        hwRmExtObjects OBJECT IDENTIFIER ::= { hwRmExt 1 }
        
        hwStaticRouteTable OBJECT-TYPE
            SYNTAX SEQUENCE OF HwStaticRouteEntry
            MAX-ACCESS not-accessible
            STATUS current
            DESCRIPTION
                "The table is used for creating static routes.
                The indexes of this table are hwStaticRouteSourceVpnName, 
                hwStaticRouteDestIpAddr,hwStaticRouteDestMaskAddr, 
                hwStaticRouteDestVpnName,hwStaticRouteNextHop,hwStaticRouteOutIfIndex."
            ::= { hwRmExtObjects 1 }
        
        hwStaticRouteEntry OBJECT-TYPE
            SYNTAX HwStaticRouteEntry
            MAX-ACCESS not-accessible
            STATUS current
            DESCRIPTION
                "The table is used for creating static routes.
                The indexes of this entry are hwStaticRouteSourceVpnName, 
                hwStaticRouteDestIpAddr,hwStaticRouteDestMaskAddr, 
                hwStaticRouteDestVpnName,hwStaticRouteNextHop,hwStaticRouteOutIfIndex."
            INDEX { hwStaticRouteSourceVpnName, hwStaticRouteDestIpAddr, hwStaticRouteDestMaskAddr, hwStaticRouteDestVpnName, hwStaticRouteNextHop, 
                hwStaticRouteOutIfIndex }
            ::= { hwStaticRouteTable 1 }

        
        HwStaticRouteEntry ::=
            SEQUENCE { 
                hwStaticRouteSourceVpnName
                    OCTET STRING,
                hwStaticRouteDestIpAddr
                    IpAddress,
                hwStaticRouteDestMaskAddr
                    IpAddress,
                hwStaticRouteDestVpnName
                    OCTET STRING,
                hwStaticRouteNextHop
                    IpAddress,
                hwStaticRouteOutIfIndex
                    Unsigned32,
                hwStaticRouteBfdName
                    OCTET STRING,
                hwStaticRoutePrefer
                    Integer32,
                hwStaticRouteDescrip
                    OCTET STRING,
                hwStaticRouteRowStatus
                    RowStatus
             }
    
                
        hwStaticRouteSourceVpnName OBJECT-TYPE
            SYNTAX OCTET STRING (SIZE (0..31))
            MAX-ACCESS not-accessible
            STATUS current
            DESCRIPTION
                "The source VPN of static routes."
            ::= { hwStaticRouteEntry 1 }

        
        hwStaticRouteDestIpAddr OBJECT-TYPE
            SYNTAX IpAddress
            MAX-ACCESS not-accessible
            STATUS current
            DESCRIPTION
                "The destination IP address of this route."
            ::= { hwStaticRouteEntry 2 }

        
        hwStaticRouteDestMaskAddr OBJECT-TYPE
            SYNTAX IpAddress
            MAX-ACCESS not-accessible
            STATUS current
            DESCRIPTION
                "Indicate the mask of the destination address."
            ::= { hwStaticRouteEntry 3 }
        
        hwStaticRouteDestVpnName OBJECT-TYPE
            SYNTAX OCTET STRING (SIZE (0..31))
            MAX-ACCESS not-accessible
            STATUS current
            DESCRIPTION
                "The destination VPN for gateway address."
            ::= { hwStaticRouteEntry 4 }

        
        hwStaticRouteNextHop OBJECT-TYPE
            SYNTAX IpAddress
            MAX-ACCESS not-accessible
            STATUS current
            DESCRIPTION
                "The next hop of static routes."
            ::= { hwStaticRouteEntry 5 }
        
        hwStaticRouteOutIfIndex OBJECT-TYPE
            SYNTAX Unsigned32
            MAX-ACCESS not-accessible
            STATUS current
            DESCRIPTION
                "The out interface ifnet index of static routes."
            ::= { hwStaticRouteEntry 6 }
        
        hwStaticRouteBfdName OBJECT-TYPE
            SYNTAX OCTET STRING (SIZE (0..15))
            MAX-ACCESS read-create
            STATUS current
            DESCRIPTION
                "The name of BFD session to whitch 
                static routes are to be bind."
            ::= { hwStaticRouteEntry 7 }

        
        hwStaticRoutePrefer OBJECT-TYPE
            SYNTAX Integer32 (1..255)
            MAX-ACCESS read-create
            STATUS current
            DESCRIPTION
                "The preference of static routes."
            ::= { hwStaticRouteEntry 8 }
        
        hwStaticRouteDescrip OBJECT-TYPE
            SYNTAX OCTET STRING (SIZE (0..35))
            MAX-ACCESS read-create
            STATUS current
            DESCRIPTION
                "The description of the static routes."
            ::= { hwStaticRouteEntry 9 }

        
        hwStaticRouteRowStatus OBJECT-TYPE
            SYNTAX RowStatus
            MAX-ACCESS read-create
            STATUS current
            DESCRIPTION
                "Indicates the row status. 
                Options: 
                1. active(1)      -when this leaf is queried, the value is fixed to active(1)
                2. createAndGo(4) -create a static route
                3. destroy(6)     -delete a static route 
                "
            ::= { hwStaticRouteEntry 10 }
        
        hwRouteStatTable OBJECT-TYPE
            SYNTAX SEQUENCE OF HwRouteStatEntry
            MAX-ACCESS not-accessible
            STATUS current
            DESCRIPTION
                "This entity is a route statistics table.
                The indexes of this table are hwRouteStatVpnName and hwRouteStatProtocolId."
            ::= { hwRmExtObjects 2 }
        
        hwRouteStatEntry OBJECT-TYPE
            SYNTAX HwRouteStatEntry
            MAX-ACCESS not-accessible
            STATUS current
            DESCRIPTION
                "This entity is a route statistics table.
                The indexes of this entry are hwRouteStatVpnName and hwRouteStatProtocolId."
            INDEX { hwRouteStatVpnName, hwRouteStatProtocolId }
            ::= { hwRouteStatTable 1 }

        
        HwRouteStatEntry ::=
            SEQUENCE { 
                hwRouteStatVpnName
                    OCTET STRING,
                hwRouteStatProtocolId
                    INTEGER,
                hwRouteStatTotal
                    Unsigned32,
                hwRouteStatActive
                    Unsigned32,
                hwRouteStatAdded
                    Unsigned32,
                hwRouteStatDeleted
                    Unsigned32,
                hwRouteStatFreed
                    Unsigned32
             }
        
        hwRouteStatVpnName OBJECT-TYPE
            SYNTAX OCTET STRING (SIZE (0..31))
            MAX-ACCESS not-accessible
            STATUS current
            DESCRIPTION
                "The name of the VPN instance for static routes."
            ::= { hwRouteStatEntry 1 }
        
        hwRouteStatProtocolId OBJECT-TYPE
            SYNTAX INTEGER
                {
                direct(1),
                static(2),
                ospf(3),
                isis(6),
                rip(7),
                bgp(8)
                }
            MAX-ACCESS not-accessible
            STATUS current
            DESCRIPTION
                "Specifies the protocol ID of the route.
                    Options:
                    1. direct(1)        -indicates the direct route
                    2. static(2)        -indicates the static route
                    3. ospf(3)          -indicates the OSPF route
                    4. isis(6)          -indicates the IS-IS route
                    5. rip(7)           -indicates the RIP route
                    6. bgp(8)           -indicates the BGP route"
            ::= { hwRouteStatEntry 2 }
        
        hwRouteStatTotal OBJECT-TYPE
            SYNTAX Unsigned32
            MAX-ACCESS read-only
            STATUS current
            DESCRIPTION
                "Total number of routes of a protocol."
            ::= { hwRouteStatEntry 3 }
        
        hwRouteStatActive OBJECT-TYPE
            SYNTAX Unsigned32
            MAX-ACCESS read-only
            STATUS current
            DESCRIPTION
                "Total number of active routes of a protocol."
            ::= { hwRouteStatEntry 4 }
        
        hwRouteStatAdded OBJECT-TYPE
            SYNTAX Unsigned32
            MAX-ACCESS read-only
            STATUS current
            DESCRIPTION
                "Total number of added routes of a protocol."
            ::= { hwRouteStatEntry 5 }
        
        hwRouteStatDeleted OBJECT-TYPE
            SYNTAX Unsigned32
            MAX-ACCESS read-only
            STATUS current
            DESCRIPTION
                "Total number of deleted routes of a protocol."
            ::= { hwRouteStatEntry 6 }
        
        hwRouteStatFreed OBJECT-TYPE
            SYNTAX Unsigned32
            MAX-ACCESS read-only
            STATUS current
            DESCRIPTION
                "Total number of released routes of a protocol."
            ::= { hwRouteStatEntry 7 }
        
        hwIpv6RouteStatTable OBJECT-TYPE
            SYNTAX SEQUENCE OF HwIpv6RouteStatEntry
            MAX-ACCESS not-accessible
            STATUS current
            DESCRIPTION
                "This entity is an IPv6 route statistics table.
                Supports the statistics of DIRECT/STATIC/BGP/OSPFv3/ISIS/RIPng routes.
                The indexes of this table are hwIpv6RouteStatVpnName and hwIpv6RouteStatProtocolId."
            ::= { hwRmExtObjects 3 }

                
        hwIpv6RouteStatEntry OBJECT-TYPE
            SYNTAX HwIpv6RouteStatEntry
            MAX-ACCESS not-accessible
            STATUS current
            DESCRIPTION
                "This entity is an IPv6 route statistics table.
                Supports the statistics of DIRECT/STATIC/BGP/OSPFv3/ISIS/RIPng routes.
                The indexes of this entry are hwIpv6RouteStatVpnName and hwIpv6RouteStatProtocolId.
                "
            INDEX { hwIpv6RouteStatVpnName, hwIpv6RouteStatProtocolId }
            ::= { hwIpv6RouteStatTable 1 }

                
        HwIpv6RouteStatEntry ::=
            SEQUENCE { 
                hwIpv6RouteStatVpnName
                    OCTET STRING,
                hwIpv6RouteStatProtocolId
                    INTEGER,
                hwIpv6RouteStatTotal
                    Unsigned32,
                hwIpv6RouteStatActive
                    Unsigned32,
                hwIpv6RouteStatAdded
                    Unsigned32,
                hwIpv6RouteStatDeleted
                    Unsigned32,
                hwIpv6RouteStatFreed
                    Unsigned32
             }
        
        hwIpv6RouteStatVpnName OBJECT-TYPE
            SYNTAX OCTET STRING (SIZE (0..31))
            MAX-ACCESS not-accessible
            STATUS current
            DESCRIPTION
                "The name of the IPv6 VPN instance for static routes."
            ::= { hwIpv6RouteStatEntry 1 }

                
        hwIpv6RouteStatProtocolId OBJECT-TYPE
            SYNTAX INTEGER
                {
                direct(1),
                static(2),
                ospf(3),
                isis(6),
                rip(7),
                bgp(8)
                }
            MAX-ACCESS not-accessible
            STATUS current
            DESCRIPTION
                "Specifies the protocol ID of the route.
                    Options:
                    1. direct(1)        -indicates the IPv6 direct route
                    2. static(2)        -indicates the IPv6 static route
                    3. ospf(3)          -indicates the IPv6 OSPF route
                    4. isis(6)          -indicates the IPv6 IS-IS route
                    5. rip(7)           -indicates the IPv6 RIP route
                    6. bgp(8)           -indicates the IPv6 BGP route"
            ::= { hwIpv6RouteStatEntry 2 }

                
        hwIpv6RouteStatTotal OBJECT-TYPE
            SYNTAX Unsigned32
            MAX-ACCESS read-only
            STATUS current
            DESCRIPTION
                "Total number of routes of a protocol."
            ::= { hwIpv6RouteStatEntry 3 }

                
        hwIpv6RouteStatActive OBJECT-TYPE
            SYNTAX Unsigned32
            MAX-ACCESS read-only
            STATUS current
            DESCRIPTION
                "Total number of active routes of a protocol."
            ::= { hwIpv6RouteStatEntry 4 }

                
        hwIpv6RouteStatAdded OBJECT-TYPE
            SYNTAX Unsigned32
            MAX-ACCESS read-only
            STATUS current
            DESCRIPTION
                "Total number of added routes of a protocol."
            ::= { hwIpv6RouteStatEntry 5 }

                
        hwIpv6RouteStatDeleted OBJECT-TYPE
            SYNTAX Unsigned32
            MAX-ACCESS read-only
            STATUS current
            DESCRIPTION
                "Total number of deleted routes of a protocol."
            ::= { hwIpv6RouteStatEntry 6 }

        
        hwIpv6RouteStatFreed OBJECT-TYPE
            SYNTAX Unsigned32
            MAX-ACCESS read-only
            STATUS current
            DESCRIPTION
                "Total number of released routes of a protocol."
            ::= { hwIpv6RouteStatEntry 7 }

        
        hwStaticRouteExtTable OBJECT-TYPE
            SYNTAX SEQUENCE OF HwStaticRouteExtEntry
            MAX-ACCESS not-accessible
            STATUS current
            DESCRIPTION
                "This entity is a static route table.
                Supports the create/destroy/modify/display operation on static routes and BFD session binding/unbinding with static routes. 
                The indexes of this table are hwStaticRouteSourceVpnNameExt, hwStaticRouteDestIpAddrExt, hwStaticRouteDestMaskAddrExt, hwStaticRouteNextHopExt, and hwStaticRouteOutIfIndexExt.
                "
            ::= { hwRmExtObjects 4 }

        
        hwStaticRouteExtEntry OBJECT-TYPE
            SYNTAX HwStaticRouteExtEntry
            MAX-ACCESS not-accessible
            STATUS current
            DESCRIPTION
                "This entity is a static route table.
                Supports the create/destroy/modify/display operation on static routes and BFD session binding/unbinding with static routes. 
                The indexes of this entry are hwStaticRouteSourceVpnNameExt, hwStaticRouteDestIpAddrExt, hwStaticRouteDestMaskAddrExt, hwStaticRouteNextHopExt, and hwStaticRouteOutIfIndexExt."
            INDEX { hwStaticRouteSourceVpnNameExt, hwStaticRouteDestIpAddrExt, hwStaticRouteDestMaskAddrExt, hwStaticRouteNextHopExt, hwStaticRouteOutIfIndexExt
                 }
            ::= { hwStaticRouteExtTable 1 }

                
        HwStaticRouteExtEntry ::=
            SEQUENCE { 
                hwStaticRouteSourceVpnNameExt
                    OCTET STRING,
                hwStaticRouteDestIpAddrExt
                    IpAddress,
                hwStaticRouteDestMaskAddrExt
                    IpAddress,
                hwStaticRouteNextHopExt
                    IpAddress,
                hwStaticRouteOutIfIndexExt
                    Unsigned32,
                hwStaticRouteDestVpnNameExt
                    OCTET STRING,
                hwStaticRouteBfdNameExt
                    OCTET STRING,
                hwStaticRoutePreferExt
                    Unsigned32,
                hwStaticRouteDescripExt
                    OCTET STRING,
                hwStaticRouteRowStatusExt
                    RowStatus,
                hwStaticRoutePermanentExt
                    INTEGER,
                hwStaticRouteLdpSyncExt
                    INTEGER
             }

        
        hwStaticRouteSourceVpnNameExt OBJECT-TYPE
            SYNTAX OCTET STRING (SIZE (0..31))
            MAX-ACCESS not-accessible
            STATUS current
            DESCRIPTION
                "The name of source VPN for static route."
            ::= { hwStaticRouteExtEntry 1 }

                
        hwStaticRouteDestIpAddrExt OBJECT-TYPE
            SYNTAX IpAddress
            MAX-ACCESS not-accessible
            STATUS current
            DESCRIPTION
                "The destination IP address of this route."
            ::= { hwStaticRouteExtEntry 2 }

                
        hwStaticRouteDestMaskAddrExt OBJECT-TYPE
            SYNTAX IpAddress
            MAX-ACCESS not-accessible
            STATUS current
            DESCRIPTION
                "The mask of the destination address."
            ::= { hwStaticRouteExtEntry 3 }

                
        hwStaticRouteNextHopExt OBJECT-TYPE
            SYNTAX IpAddress
            MAX-ACCESS not-accessible
            STATUS current
            DESCRIPTION
                "The next hop of static route."
            ::= { hwStaticRouteExtEntry 4 }

                
        hwStaticRouteOutIfIndexExt OBJECT-TYPE
            SYNTAX Unsigned32
            MAX-ACCESS not-accessible
            STATUS current
            DESCRIPTION
                "The ifnet index of the outgoing interface of static route."
            ::= { hwStaticRouteExtEntry 5 }

                
        hwStaticRouteDestVpnNameExt OBJECT-TYPE
            SYNTAX OCTET STRING (SIZE (0..31))
            MAX-ACCESS read-create
            STATUS current
            DESCRIPTION
                "The name of the destination VPN for gateway address."
            ::= { hwStaticRouteExtEntry 6 }

                
        hwStaticRouteBfdNameExt OBJECT-TYPE
            SYNTAX OCTET STRING (SIZE (0..15))
            MAX-ACCESS read-create
            STATUS current
            DESCRIPTION
                "The name of BFD session to whitch 
                static route is to be bound."
            ::= { hwStaticRouteExtEntry 7 }

                
        hwStaticRoutePreferExt OBJECT-TYPE
            SYNTAX Unsigned32 (1..255)
            MAX-ACCESS read-create
            STATUS current
            DESCRIPTION
                "The preference of static route."
            ::= { hwStaticRouteExtEntry 8 }

                
        hwStaticRouteDescripExt OBJECT-TYPE
            SYNTAX OCTET STRING (SIZE (0..35))
            MAX-ACCESS read-create
            STATUS current
            DESCRIPTION
                "The description of static route."
            ::= { hwStaticRouteExtEntry 9 }
        
        hwStaticRouteRowStatusExt OBJECT-TYPE
            SYNTAX RowStatus
            MAX-ACCESS read-create
            STATUS current
            DESCRIPTION
                "The operation for static route."
            ::= { hwStaticRouteExtEntry 10 }

        
        hwStaticRoutePermanentExt OBJECT-TYPE
            SYNTAX INTEGER
                {
                none(0),
                permanent(1)
                }
            MAX-ACCESS read-create
            STATUS current
            DESCRIPTION
                "Specifies the permanent-Advertising attribute of the static route:
                    Options:
                    1. none(0)          -indicates that the permanent-Advertising attribute is not specified  
                    2. permanent(1)     -indicates that the permanent-Advertising attribute is specified"
            ::= { hwStaticRouteExtEntry 11 }

        
        hwStaticRouteLdpSyncExt OBJECT-TYPE
            SYNTAX INTEGER
                {
                none(0),
                ldpsync(1)
                }
            MAX-ACCESS read-create
            STATUS current
            DESCRIPTION
                "Specifies the LdpSync-Advertising attribute of the static route:
                    Options:
                    1. none(0)       -indicates that the LdpSync-Advertising attribute is not specified 
                    2. ldpsync(1)    -indicates that the LdpSync-Advertising attribute is specified"
            ::= { hwStaticRouteExtEntry 12 }


        hwRmExtConformance OBJECT IDENTIFIER ::= { hwRmExt 2 }


        hwRmExtCompliances OBJECT IDENTIFIER ::= { hwRmExtConformance 1 }


        hwRmExtCompliance MODULE-COMPLIANCE
            STATUS current
            DESCRIPTION 
                "The compliance statement for Route Management MIB."
            MODULE 
                MANDATORY-GROUPS { hwStaticRouteGroup, hwRouteStatGroup, hwStaticRouteExtGroup, hwIpv6RouteStatGroup }
            ::= { hwRmExtCompliances 1 }


        hwRmExtGroups OBJECT IDENTIFIER ::= { hwRmExtConformance 2 }


        hwStaticRouteGroup OBJECT-GROUP
            OBJECTS { hwStaticRouteBfdName, hwStaticRoutePrefer, hwStaticRouteDescrip, hwStaticRouteRowStatus }
            STATUS current
            DESCRIPTION 
                "Static routes table group."
            ::= { hwRmExtGroups 1 }


        hwRouteStatGroup OBJECT-GROUP
            OBJECTS { hwRouteStatTotal, hwRouteStatActive, hwRouteStatAdded, hwRouteStatDeleted, hwRouteStatFreed
                 }
            STATUS current
            DESCRIPTION 
                "Route statistic table group."
            ::= { hwRmExtGroups 2 }


        hwIpv6RouteStatGroup OBJECT-GROUP
            OBJECTS { hwIpv6RouteStatTotal, hwIpv6RouteStatActive, hwIpv6RouteStatAdded, hwIpv6RouteStatDeleted, hwIpv6RouteStatFreed
                 }
            STATUS current
            DESCRIPTION 
                "Route statistic table group."
            ::= { hwRmExtGroups 3 }


        hwStaticRouteExtGroup OBJECT-GROUP
            OBJECTS { hwStaticRouteDestVpnNameExt, hwStaticRouteBfdNameExt, hwStaticRoutePreferExt, hwStaticRouteRowStatusExt, hwStaticRouteDescripExt, 
                hwStaticRoutePermanentExt, hwStaticRouteLdpSyncExt }
            STATUS current
            DESCRIPTION 
                "Static route table group."
            ::= { hwRmExtGroups 4 }


        hwTunnelExtObjects OBJECT IDENTIFIER ::= { hwRmExt 3 }

        
        hwTnl2L3vpnTable OBJECT-TYPE
            SYNTAX SEQUENCE OF HwTnl2L3vpnEntry
            MAX-ACCESS not-accessible
            STATUS current
            DESCRIPTION
                "This object indicates the tunnel ID and L3VPN table of this entity.
                The indexes of this table are hwL3vpnTnlId and hwVpnIndex."
            ::= { hwTunnelExtObjects 1 }

        hwTnl2L3vpnEntry OBJECT-TYPE
            SYNTAX HwTnl2L3vpnEntry
            MAX-ACCESS not-accessible
            STATUS current
            DESCRIPTION
                "This object indicates the tunnel ID and L3VPN table of this entity.
                The indexes of this entry are hwL3vpnTnlId and hwVpnIndex."
            INDEX { hwL3vpnTnlId, hwVpnIndex }
            ::= { hwTnl2L3vpnTable 1 }

        
        HwTnl2L3vpnEntry ::=
            SEQUENCE { 
                hwL3vpnTnlId
                    Unsigned32,
                hwVpnIndex
                    Unsigned32,
                hwVpnName
                    OCTET STRING
             }

        hwL3vpnTnlId OBJECT-TYPE
            SYNTAX Unsigned32
            MAX-ACCESS not-accessible
            STATUS current
            DESCRIPTION
                "The object indicates the tunnel ID."
            ::= { hwTnl2L3vpnEntry 1 }

        
        hwVpnIndex OBJECT-TYPE
            SYNTAX Unsigned32 (0..4096)
            MAX-ACCESS not-accessible
            STATUS current
            DESCRIPTION
                "The object indicates the VRF index of a VPN."
            ::= { hwTnl2L3vpnEntry 2 }

        hwVpnName OBJECT-TYPE
            SYNTAX OCTET STRING (SIZE (0..31))
            MAX-ACCESS read-only
            STATUS current
            DESCRIPTION
                "The object indicates the VPN name."
            ::= { hwTnl2L3vpnEntry 3 }

        hwTnl2VplsTable OBJECT-TYPE
            SYNTAX SEQUENCE OF HwTnl2VplsEntry
            MAX-ACCESS not-accessible
            STATUS current
            DESCRIPTION
                "The object indicates the tunnel ID and VPLS table of this entity.
                The indexes of this table are hwVplsTnlId and hwVplsVcId."
            ::= { hwTunnelExtObjects 2 }

        hwTnl2VplsEntry OBJECT-TYPE
            SYNTAX HwTnl2VplsEntry
            MAX-ACCESS not-accessible
            STATUS current
            DESCRIPTION
                "The object indicates the tunnel ID and VPLS table of this entity.
                The indexes of this entry are hwVplsTnlId and hwVplsVcId."
            INDEX { hwVplsTnlId, hwVplsVcId }
            ::= { hwTnl2VplsTable 1 }

        
        HwTnl2VplsEntry ::=
            SEQUENCE { 
                hwVplsTnlId
                    Unsigned32,
                hwVplsVcId
                    Unsigned32,
                hwVsiIndex
                    Unsigned32,
                hwVsiId
                    Unsigned32,
                hwVsiName
                    OCTET STRING,
                hwVplsVcType
                    Unsigned32,
                hwVplsPeerIp
                    IpAddress
             }

        hwVplsTnlId OBJECT-TYPE
            SYNTAX Unsigned32
            MAX-ACCESS not-accessible
            STATUS current
            DESCRIPTION
                "The object indicates the tunnel ID."
            ::= { hwTnl2VplsEntry 1 }

        hwVplsVcId OBJECT-TYPE
            SYNTAX Unsigned32
            MAX-ACCESS not-accessible
            STATUS current
            DESCRIPTION
                "The object indicates the VC ID of a VPLS."
            ::= { hwTnl2VplsEntry 2 }

        hwVsiIndex OBJECT-TYPE
            SYNTAX Unsigned32
            MAX-ACCESS read-only
            STATUS current
            DESCRIPTION
                "The object indicates the VSI index of a VPLS."
            ::= { hwTnl2VplsEntry 3 }

        hwVsiId OBJECT-TYPE
            SYNTAX Unsigned32
            MAX-ACCESS read-only
            STATUS current
            DESCRIPTION
                "The object indicates the VSI ID of a VPLS."
            ::= { hwTnl2VplsEntry 4 }

        hwVsiName OBJECT-TYPE
            SYNTAX OCTET STRING (SIZE (0..31))
            MAX-ACCESS read-only
            STATUS current
            DESCRIPTION
                "The object indicates the VSI name of a VPLS."
            ::= { hwTnl2VplsEntry 5 }

        
        hwVplsVcType OBJECT-TYPE
            SYNTAX Unsigned32
            MAX-ACCESS read-only
            STATUS current
            DESCRIPTION
                "The object indicates the VC type of a VPLS."
            ::= { hwTnl2VplsEntry 6 }

        hwVplsPeerIp OBJECT-TYPE
            SYNTAX IpAddress
            MAX-ACCESS read-only
            STATUS current
            DESCRIPTION
                "The object indicates the peer IP address of a VPLS."
            ::= { hwTnl2VplsEntry 7 }

        hwTnl2Pwe3VllTable OBJECT-TYPE
            SYNTAX SEQUENCE OF HwTnl2Pwe3VllEntry
            MAX-ACCESS not-accessible
            STATUS current
            DESCRIPTION
                "The object indicates the tunnel ID and PWE3/VLL table of this entity.
                The indexes of this table are hwPwVllTnlId and hwAcIndex."
            ::= { hwTunnelExtObjects 3 }

        
        hwTnl2Pwe3VllEntry OBJECT-TYPE
            SYNTAX HwTnl2Pwe3VllEntry
            MAX-ACCESS not-accessible
            STATUS current
            DESCRIPTION
                "The object indicates the tunnel ID and PWE3/VLL table of this entity.
                The indexes of this entry are hwPwVllTnlId and hwAcIndex."
            INDEX { hwPwVllTnlId, hwAcIndex }
            ::= { hwTnl2Pwe3VllTable 1 }

        
        HwTnl2Pwe3VllEntry ::=
            SEQUENCE { 
                hwPwVllTnlId
                    Unsigned32,
                hwAcIndex
                    Unsigned32,
                hwPwVllIfName
                    OCTET STRING,
                hwMasterSlaveFlag
                    Unsigned32,
                hwPwVllPeerIp
                    IpAddress,
                hwPwVllVcId
                    Unsigned32,
                hwPwVllSvcFlag
                    Unsigned32,
                hwPwVcType
                    INTEGER,
                hwSvcReceiveLabel
                    Unsigned32,
                hwSvcTransmitLabel
                    Unsigned32
             }

        hwPwVllTnlId OBJECT-TYPE
            SYNTAX Unsigned32
            MAX-ACCESS not-accessible
            STATUS current
            DESCRIPTION
                "The object indicates the tunnel ID."
            ::= { hwTnl2Pwe3VllEntry 1 }

        hwAcIndex OBJECT-TYPE
            SYNTAX Unsigned32
            MAX-ACCESS not-accessible
            STATUS current
            DESCRIPTION
                "The object indicates the AC index of a PWE3."
            ::= { hwTnl2Pwe3VllEntry 2 }

        
        hwPwVllIfName OBJECT-TYPE
            SYNTAX OCTET STRING (SIZE (1..64))
            MAX-ACCESS read-only
            STATUS current
            DESCRIPTION
                "The object indicates the interface name of a PWE3."
            ::= { hwTnl2Pwe3VllEntry 3 }

        
        hwMasterSlaveFlag OBJECT-TYPE
            SYNTAX Unsigned32
            MAX-ACCESS read-only
            STATUS current
            DESCRIPTION
                "The object indicates the master and slave flags of a PWE3."
            ::= { hwTnl2Pwe3VllEntry 4 }

        hwPwVllPeerIp OBJECT-TYPE
            SYNTAX IpAddress
            MAX-ACCESS read-only
            STATUS current
            DESCRIPTION
                "The object indicates the peer IP address of a PWE3."
            ::= { hwTnl2Pwe3VllEntry 5 }

        
        hwPwVllVcId OBJECT-TYPE
            SYNTAX Unsigned32
            MAX-ACCESS read-only
            STATUS current
            DESCRIPTION
                "The object indicates the VC ID of a PWE3."
            ::= { hwTnl2Pwe3VllEntry 6 }

        
        hwPwVllSvcFlag OBJECT-TYPE
            SYNTAX Unsigned32
            MAX-ACCESS read-only
            STATUS current
            DESCRIPTION
                "This object indicates the type of a PWE3. 
                Static PWs (1)
                Dynamic PWs (0)"
            ::= { hwTnl2Pwe3VllEntry 7 }

        hwPwVcType OBJECT-TYPE
            SYNTAX INTEGER
                {
                frameRelayDlciMartini(1),
                atmAal5SduVccTransport(2),
                atmTransparentCellTransport(3),
                vlan(4),
                ethernet(5),
                hdlc(6),
                ppp(7),
                cem(8),
                atmN2OneVccCellTransport(9),
                atmN2OneVpcCellTransport(10),
                ipLayer2Transport(11),
                atmOne2OneVccCellMode(12),
                atmOne2OneVpcCellMode(13),
                atmAal5PduVccTransport(14),
                frameRelayPortMode(15),
                cep(16),
                saE1oP(17),
                saT1oP(18),
                saE3oP(19),
                saT3oP(20),
                cESoPsnBasicMode(21),
                tDMoIPbasicMode(22),
                l2VpnCESoPSNTDMwithCAS(23),
                l2VpnTDMoIPTDMwithCAS(24),
                frameRelayDlci(25),
                ipInterworking(64),
                unknown(255)
                }
            MAX-ACCESS read-only
            STATUS current
            DESCRIPTION
                "Specifies an indication of the L2Vpn's VC encapsulation type:
                    Options:
                    1: frameRelayDlciMartini(1)       -indicates that the encapsulation type is Frame Relay DLCI(Martini Mode).
                    2: atmAal5SduVccTransport(2)      -indicates that the encapsulation type is ATM AAL5 SDU VCC transport.
                    3: atmTransparentCellTransport(3) -indicates that the encapsulation type is ATM transparent cell transport.
                    4: vlan(4)                        -indicates that the encapsulation type is Vlan.
                    5: ethernet(5)                    -indicates that the encapsulation type is Ethernet.
                    6: hdlc(6)                        -indicates that the encapsulation type is HDLC.
                    7: ppp(7)                         -indicates that the encapsulation type is PPP.
                    8: cem(8)                         -indicates that the encapsulation type is SONET/SDH Circuit Emulation Service Over MPLS(CEM).
                    9: atmN2OneVccCellTransport(9)    -indicates that the encapsulation type is ATM n-to-one VCC cell transport.
                    10: atmN2OneVpcCellTransport(10)  -indicates that the encapsulation type is ATM n-to-one VPC cell transport.
                    11: ipLayer2Transport(11)         -indicates that the encapsulation type is IP Layer2 Transport.
                    12: atmOne2OneVccCellMode(12)     -indicates that the encapsulation type is ATM one-to-one VCC Cell Mode.
                    13: atmOne2OneVpcCellMode(13)     -indicates that the encapsulation type is ATM one-to-one VPC Cell Mode.
                    14: atmAal5PduVccTransport(14)    -indicates that the encapsulation type is ATM AAL5 PDU VCC transport.
                    15: frameRelayPortMode(15)        -indicates that the encapsulation type is Frame-Relay Port mode.
                    16: cep(16)                       -indicates that the encapsulation type is SONET/SDH Circuit Emulation over Packet (CEP).
                    17: saE1oP(17)                    -indicates that the encapsulation type is Structure-agnostic E1 over Packet (SAE1oP).
                    18: saT1oP(18)                    -indicates that the encapsulation type is Structure-agnostic T1 (DS1) over Packet (SAT1oP).
                    19: saE3oP(19)                    -indicates that the encapsulation type is Structure-agnostic E3 over Packet (SAE3oP).
                    20: saT3oP(20)                    -indicates that the encapsulation type is Structure-agnostic T3 (DS3) over Packet (SAT3oP).
                    21: cESoPsnBasicMode(21)          -indicates that the encapsulation type is CESoPSN basic mode.
                    22: tDMoIPbasicMode(22)           -indicates that the encapsulation type is TDMoIP basic mode.
                    23: l2VpnCESoPSNTDMwithCAS(23)    -indicates that the encapsulation type is CESoPSN TDM with CAS.
                    24: l2VpnTDMoIPTDMwithCAS(24)     -indicates that the encapsulation type is TDMoIP TDM with CAS.
                    25: frameRelayDlci(25)            -indicates that the encapsulation type is Frame Relay DLCI.
                    26: ipInterworking(64)            -indicates that the encapsulation type is IP-interworking.
                    27: unknown(255)                  -indicates the unknown encapsulation type.
                "
            ::= { hwTnl2Pwe3VllEntry 8 }

        hwSvcReceiveLabel OBJECT-TYPE
            SYNTAX Unsigned32
            MAX-ACCESS read-only
            STATUS current
            DESCRIPTION
                "This object indicates the inbound label."
            ::= { hwTnl2Pwe3VllEntry 9 }

        
        hwSvcTransmitLabel OBJECT-TYPE
            SYNTAX Unsigned32
            MAX-ACCESS read-only
            STATUS current
            DESCRIPTION
                "This object indicates the outbound label."
            ::= { hwTnl2Pwe3VllEntry 10 }

        
        hwTnlIf2TnlIdTable OBJECT-TYPE
            SYNTAX SEQUENCE OF HwTnlIf2TnlIdEntry
            MAX-ACCESS not-accessible
            STATUS current
            DESCRIPTION
                "This object indicates the tunnel interface and tunnel ID table of this entity.
                The index of this table is hwTunnelIf."
            ::= { hwTunnelExtObjects 4 }

        
        hwTnlIf2TnlIdEntry OBJECT-TYPE
            SYNTAX HwTnlIf2TnlIdEntry
            MAX-ACCESS not-accessible
            STATUS current
            DESCRIPTION
                "This object indicates the tunnel interface and tunnel ID table of this entity.
                The index of this entry is hwTunnelIf."
            INDEX { hwTunnelIf }
            ::= { hwTnlIf2TnlIdTable 1 }

        
        HwTnlIf2TnlIdEntry ::=
            SEQUENCE { 
                hwTunnelIf
                    OCTET STRING,
                hwTunnelId
                    Unsigned32
             }

        hwTunnelIf OBJECT-TYPE
            SYNTAX OCTET STRING (SIZE (1..64))
            MAX-ACCESS not-accessible
            STATUS current
            DESCRIPTION
                "The object indicates the tunnel interface name."
            ::= { hwTnlIf2TnlIdEntry 1 }

        
        hwTunnelId OBJECT-TYPE
            SYNTAX Unsigned32
            MAX-ACCESS read-only
            STATUS current
            DESCRIPTION
                "The object indicates the tunnel ID."
            ::= { hwTnlIf2TnlIdEntry 2 }

        
        hwTnl2MultiHopPwe3Table OBJECT-TYPE
            SYNTAX SEQUENCE OF HwTnl2MultiHopPwe3Entry
            MAX-ACCESS not-accessible
            STATUS current
            DESCRIPTION
                "This object indicates the tunnel ID and Multi-hop PWE3 table of this entity.
                The indexes of this table are hwMultiHopPwe3TnlId, hwMultiHopPwe3VcType, and hwMultiHopPwe3VcId."
            ::= { hwTunnelExtObjects 5 }

        
        hwTnl2MultiHopPwe3Entry OBJECT-TYPE
            SYNTAX HwTnl2MultiHopPwe3Entry
            MAX-ACCESS not-accessible
            STATUS current
            DESCRIPTION
                "This object indicates the tunnel ID and Multi-hop PWE3 table of this entity.
                The indexes of this entry are hwMultiHopPwe3TnlId, hwMultiHopPwe3VcType, and hwMultiHopPwe3VcId."
            INDEX { hwMultiHopPwe3TnlId, hwMultiHopPwe3VcType, hwMultiHopPwe3VcId }
            ::= { hwTnl2MultiHopPwe3Table 1 }

        
        HwTnl2MultiHopPwe3Entry ::=
            SEQUENCE { 
                hwMultiHopPwe3TnlId
                    Unsigned32,
                hwMultiHopPwe3VcType
                    Unsigned32,
                hwMultiHopPwe3VcId
                    Unsigned32,
                hwMultiHopPwe3PeerIp
                    IpAddress
             }

        hwMultiHopPwe3TnlId OBJECT-TYPE
            SYNTAX Unsigned32
            MAX-ACCESS not-accessible
            STATUS current
            DESCRIPTION
                "The object indicates the tunnel ID."
            ::= { hwTnl2MultiHopPwe3Entry 1 }

        
        hwMultiHopPwe3VcType OBJECT-TYPE
            SYNTAX Unsigned32
            MAX-ACCESS not-accessible
            STATUS current
            DESCRIPTION
                "The object indicates the VC type of a Multi-hop PWE3."
            ::= { hwTnl2MultiHopPwe3Entry 2 }

        
        hwMultiHopPwe3VcId OBJECT-TYPE
            SYNTAX Unsigned32
            MAX-ACCESS not-accessible
            STATUS current
            DESCRIPTION
                "The object indicates the VC ID of a Multi-hop PWE3."
            ::= { hwTnl2MultiHopPwe3Entry 3 }

        
        hwMultiHopPwe3PeerIp OBJECT-TYPE
            SYNTAX IpAddress
            MAX-ACCESS read-only
            STATUS current
            DESCRIPTION
                "The object indicates the peer IP address of a Multi-hop PWE3."
            ::= { hwTnl2MultiHopPwe3Entry 4 }

        
        hwTunnelExtConformance OBJECT IDENTIFIER ::= { hwRmExt 4 }

        
        hwTunnelExtCompliances OBJECT IDENTIFIER ::= { hwTunnelExtConformance 1 }

        
        hwTunnelExtCompliance MODULE-COMPLIANCE
            STATUS current
            DESCRIPTION 
                "The object indicates the compliance statement for route management MIB."
            MODULE 
                MANDATORY-GROUPS { hwTnl2L3vpnGroup, hwTnl2VplsGroup, hwTnl2Pwe3VllGroup, hwTnlIf2TnlIdGroup, hwTnl2MultiHopPwe3Group
                     }
            ::= { hwTunnelExtCompliances 1 }

        
        hwTunnelExtGroups OBJECT IDENTIFIER ::= { hwTunnelExtConformance 2 }

        
        hwTnl2L3vpnGroup OBJECT-GROUP
            OBJECTS { hwVpnName }
            STATUS current
            DESCRIPTION 
                "The object indicates the tunnel ID and L3VPN table group."
            ::= { hwTunnelExtGroups 1 }

        
        hwTnl2VplsGroup OBJECT-GROUP
            OBJECTS { hwVsiIndex, hwVsiId, hwVsiName, hwVplsVcType, hwVplsPeerIp
                 }
            STATUS current
            DESCRIPTION 
                "The object indicates the tunnel ID and VPLS table group."
            ::= { hwTunnelExtGroups 2 }

        
        hwTnl2Pwe3VllGroup OBJECT-GROUP
            OBJECTS { hwMasterSlaveFlag, hwPwVllIfName, hwPwVllVcId, hwPwVllSvcFlag, hwPwVcType, 
                hwSvcReceiveLabel, hwSvcTransmitLabel, hwPwVllPeerIp }
            STATUS current
            DESCRIPTION 
                "The object indicates the tunnel ID and PWE3/VLL table group."
            ::= { hwTunnelExtGroups 3 }

        
        hwTnlIf2TnlIdGroup OBJECT-GROUP
            OBJECTS { hwTunnelId }
            STATUS current
            DESCRIPTION 
                "The object indicates the tunnel interface name and tunnel ID table group."
            ::= { hwTunnelExtGroups 4 }

        
        hwTnl2MultiHopPwe3Group OBJECT-GROUP
            OBJECTS { hwMultiHopPwe3PeerIp }
            STATUS current
            DESCRIPTION 
                "The object indicates the tunnel ID and Multi-hop PWE3 table group."
            ::= { hwTunnelExtGroups 5 }

        
        hwTnlGroupTrapObjects OBJECT IDENTIFIER ::= { hwRmExt 5 }

        
        hwTnlDestionation OBJECT-TYPE
            SYNTAX IpAddress
            MAX-ACCESS accessible-for-notify
            STATUS current
            DESCRIPTION
                "The destination of the tunnel group."
            ::= { hwTnlGroupTrapObjects 1 }

        
        hwTnlPolicy OBJECT-TYPE
            SYNTAX OCTET STRING (SIZE (1..39))
            MAX-ACCESS accessible-for-notify
            STATUS current
            DESCRIPTION
                "Tunnel policy name."
            ::= { hwTnlGroupTrapObjects 2 }

        
        hwTnlGroupTraps OBJECT IDENTIFIER ::= { hwRmExt 6 }

        
        hwTunnelGroupUp NOTIFICATION-TYPE
            OBJECTS { hwTnlDestionation, hwTnlPolicy }
            STATUS current
            DESCRIPTION 
                "Tunnels selected by the applications are defined by the next hop and the tunnel policy. 
                If all the tunnels used for load balancing are Down, this trap will be sent to the user."
            ::= { hwTnlGroupTraps 1 }

        
        hwTunnelGroupDown NOTIFICATION-TYPE
            OBJECTS { hwTnlDestionation, hwTnlPolicy }
            STATUS current
            DESCRIPTION 
                "Tunnels selected by the applications are defined by the next hop and the tunnel policy. If any one of the tunnels used for load balancing is Up, this trap will be sent to the user. "
            ::= { hwTnlGroupTraps 2 }

        
        hwTnlGroupTrapConformance OBJECT IDENTIFIER ::= { hwRmExt 7 }

        
        hwTnlGroupNotificationGroup NOTIFICATION-GROUP
            NOTIFICATIONS { hwTunnelGroupUp, hwTunnelGroupDown }
            STATUS current
            DESCRIPTION 
                "The object indicates the Up/Down state of the tunnel group."
            ::= { hwTnlGroupTrapConformance 1 }

        
        hwTnlGroupObjectGroup OBJECT-GROUP
            OBJECTS { hwTnlDestionation, hwTnlPolicy }
            STATUS current
            DESCRIPTION 
                "The object indicates the compliance statement for tunnel group trap."
            ::= { hwTnlGroupTrapConformance 2 }

        
    
    END
