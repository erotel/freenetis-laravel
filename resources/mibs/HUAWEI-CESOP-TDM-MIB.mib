-- ================================================================================
-- Copyright (C) 2011 by  HUAWEI TECHNOLOGIES. All rights reserved.
-- Description: The MIB is used for defining huawei's CESoP management MIB objects.
-- Reference:
-- Version: V1.19
-- ================================================================================

  HUAWEI-CESOP-TDM-MIB DEFINITIONS ::= BEGIN
    IMPORTS
      huaweiMgmt
        FROM HUAWEI-MIB
      IpAddress, Unsigned32, Counter32, Counter64, OBJECT-TYPE, MODULE-IDENTITY, Integer32,Gauge32,NOTIFICATION-TYPE
        FROM SNMPv2-SMI
      DisplayString, RowStatus, TruthValue, MacAddress, DateAndTime
        FROM SNMPv2-TC
      InterfaceIndex ,ifIndex
        FROM IF-MIB;

    hwCesop MODULE-IDENTITY
      LAST-UPDATED "201305200900Z"
      ORGANIZATION "Huawei Technologies Co.,Ltd."
      CONTACT-INFO
        "Huawei Industrial Base
         Bantian, Longgang
         Shenzhen 518129
         People's Republic of China
         Website: http://www.huawei.com
         Email: support@huawei.com
        "
      DESCRIPTION  "The MIB is used for defining huawei's CESoP management MIB objects."

--  Revision history
      REVISION     "201305200900Z"
      DESCRIPTION  "V1.19, add leaf nodes hwCesopGateway, hwCesopRcvSsrcId, hwCesopTxSsrcId, 
                    hwCesopPayloadType, hwCesopSnStartNum and hwCesopRemoteMacStatus in table 
                    hwCesopConnectCfgTable. Add hwCesopConnectPacketReceiveErrorCount and 
                    hwCesopConnectPacketReceiveSSrcErrorCount in table hwCesopConnectPerfTable.
                   "

      REVISION     "201305150900Z"
      DESCRIPTION  "V1.18, modify enum name of leaf node hwCesopPortClockSource to syetem(1), 
                    line(2), net(5), net1(6), net2(7), net3(8).
                    "
                   
      REVISION     "201106250900Z"
      DESCRIPTION  "V1.17, add leaf nodes hwCesopRcvLSPLabel, hwCesopRcvPWLabel,  hwCesopTransLSPLabel
                   and hwCesopTransPWLabel in table hwCesopConnectCfgTable for creating CESoP link in
                   MxU with mpls + mpls encapsulation.
                   "

      REVISION     "201104280900Z"
      DESCRIPTION  "V1.16, add leaf nodes hwCesopTDMLoadTime, hwCesopPriority and hwCesopTDMVCLIndex
                   in table hwCesopConnectCfgTable for creating CESoP link in MxU; modify the default
                   value of hwCesopRTPEnable and the scope of the value of hwCesopJitterBuffer.
                   "

      REVISION     "201012080900Z"
      DESCRIPTION  "V1.15, modify enum value of leaf node hwCesopPortClockSource to e1Syetem(1),
                    e1Line(2), e1Net(5), e1Net1(6), e1Net2(7), e1Net3(8), invalid(-1).
                   "

      REVISION     "201011090900Z"
      DESCRIPTION  "V1.14, modified the description of MIB. "

      REVISION     "201010140900Z"
      DESCRIPTION  "V1.13, add enumerate invalid(-1) for leaf hwCesopPortRTPSwitch.
                   "

      REVISION     "201009260900Z"
      DESCRIPTION  "V1.12, add leaf node hwCesopPortFrameMode in table hwCesopPortCfgTable
                    for setting the frame mode.
                   "

      REVISION     "201009100900Z"
      DESCRIPTION  "V1.11, add the following leaves in hwCesopConnectPerfTable table:
                    hwCesopConnectChannelInPkts,
                    hwCesopConnectChannelOutPkts,
                    hwCesopConnectChannelInSequenceErrors,
                    hwCesopConnectChannelInVlanInvalid,
                    hwCesopQueueUnderflow,
                    hwCesopQueueOverflow.
                    add enum invalid(-1) for leaf hwCesopConnectPerfClearStat.
                   "

      REVISION     "201007260900Z"
      DESCRIPTION  "V1.10, modified the description of MIB.
                    added enum t1B8SZ(3) in hwCesopPortLineCoding leaf.
                   "

      REVISION     "201004260900Z"
      DESCRIPTION  "V1.09, modified the syntax error.

                   "

      REVISION     "201004010900Z"
      DESCRIPTION  "V1.08, modified the syntax error.                              "

      REVISION     "201001070900Z"
      DESCRIPTION  "V1.07, added leaf node hwCesopPortRTPSwitch in table hwCesopPortCfgEntry
                      for setting the RTP switch. "

      REVISION     "200910150900Z"
      DESCRIPTION  "V1.05, added leaf node hwCesopTDMPayloadSize in table hwCesopConnectCfgTable
                      for setting the length of payload."

      REVISION     "200902110900Z"
      DESCRIPTION  "V1.03, added leaf node hwCesopBoardRecoveryClockSource in table hwCesopBoardCfgTable
                      for setting recovery clock source of board.                              -
                    Modified the name of leaf node hwCesopBoardIpOperStatus to hwCesopBoardOperStatus.
                   "

      REVISION     "200802140900Z"
      DESCRIPTION  "V1.00, initial version."

      ::= { huaweiMgmt 108 }

    hwCesopMibObjects OBJECT IDENTIFIER ::= { hwCesop 1 }

    hwCesopPortCfgTable OBJECT-TYPE
      SYNTAX SEQUENCE OF HwCesopPortCfgEntry
      MAX-ACCESS not-accessible
      STATUS current
      DESCRIPTION
        "This table is used for setting CESoP port configuration.
         The index of this table is ifIndex.
        "
      ::= { hwCesopMibObjects 1 }

    hwCesopPortCfgEntry OBJECT-TYPE
      SYNTAX HwCesopPortCfgEntry
      MAX-ACCESS not-accessible
      STATUS current
      DESCRIPTION
        "This table is used for setting CESoP port configuration.
         The index of this entry is ifIndex.
        "
      INDEX { ifIndex }
      ::= { hwCesopPortCfgTable 1 }

    HwCesopPortCfgEntry ::=
      SEQUENCE
        {
        hwCesopPortLineCoding     INTEGER,
        hwCesopPortLoopback       INTEGER,
        hwCesopPortClockSource    INTEGER,
        hwCesopPortLineStatus     INTEGER,
        hwCesopPortRTPSwitch      INTEGER,
        hwCesopPortFrameMode      INTEGER
        }

    hwCesopPortLineCoding OBJECT-TYPE
      SYNTAX INTEGER
        {
         e1HDB3(1),
         e1AMI(2),
         t1B8SZ(3)
        }
      MAX-ACCESS read-write
      STATUS current
      DESCRIPTION
        "Line coding mode of CESoP port.
         Options:
         1. e1HDB3(1)  -the line coding mode of CESoP port is e1HDB3
         2. e1AMI(2)   -the line coding mode of CESoP port is e1AMI
         3. t1B8SZ(3)  -the line coding mode of CESoP port is t1B8SZ
        "
      ::= { hwCesopPortCfgEntry 1 }

    hwCesopPortLoopback OBJECT-TYPE
      SYNTAX INTEGER
        {
        e1NoLoop(1),
        e1LocalLoop(2),
        e1RemoteLoop(3),
        e1PayloadLoop(7)
        }
      MAX-ACCESS read-write
      STATUS current
      DESCRIPTION
        "Loopback mode of CESoP port.
         Options:
         1. e1NoLoop(1)        -the loopback mode of CESoP port is e1NoLoop
         2. e1LocalLoop(2)     -the loopback mode of CESoP port is e1LocalLoop
         3. e1RemoteLoop(3)    -the loopback mode of CESoP port is e1RemoteLoop
         4. e1PayloadLoop(7)   -the loopback mode of CESoP port is e1PayloadLoop
        "
      ::= { hwCesopPortCfgEntry 2 }

    hwCesopPortClockSource OBJECT-TYPE
      SYNTAX INTEGER
        {    
         syetem(1),
         line(2),
         net(5),
         net1(6),
         net2(7),
         net3(8),
         invalid(-1)
        }
      MAX-ACCESS read-write
      STATUS current
      DESCRIPTION
        "Clock source mode of CESoP port.
         Options:
         1. syetem(1)     -system clock
         2. line(2)       -line clock
         3. net(5)        -net clock
         4. net1(6)       -net clock 1
         5. net2(7)       -net clock 2
         6. net3(8)       -net clock 3
         7. invalid(-1)   -invalid value
        "
      ::= { hwCesopPortCfgEntry 3 }

    hwCesopPortLineStatus OBJECT-TYPE
      SYNTAX INTEGER
       {
         dsx1Normal(1),
         dsx1Fault(2)
       }
      MAX-ACCESS read-only
      STATUS current
      DESCRIPTION
        "Line status of CESoP port.
         Options:
         1. dsx1Normal(1)  -the line alarm status of CESoP port is normal
         2. dsx1Fault(2)   -the line alarm status of CESoP port is fault
        "
      ::= { hwCesopPortCfgEntry 4 }

    hwCesopPortRTPSwitch OBJECT-TYPE
      SYNTAX INTEGER
       {
         enable(1),
         disable(2),
         invalid(-1)
       }
      MAX-ACCESS read-write
      STATUS current
      DESCRIPTION
        "Status of RTP switch.
         Options:
         1. enable(1)        -status of RTP switch to enable
         2. disable(2)       -status of RTP switch to disable
         3. invalid(-1)      -invalid value
        "
        DEFVAL {enable}
      ::= { hwCesopPortCfgEntry 5 }

    hwCesopPortFrameMode OBJECT-TYPE
      SYNTAX INTEGER
       {
         t1SF(1),
         t1ESF(2),
         invalid(-1)
       }
      MAX-ACCESS read-write
      STATUS current
      DESCRIPTION
        "Frame mode of CESoP port.
         Options:
         1. t1SF(1)       -the frame mode of CESoP port is SF
         2. t1ESF(2)      -the frame mode of CESoP port is ESF
         3. invalid(-1)   -invalid value
         "
         DEFVAL {t1ESF}
      ::= { hwCesopPortCfgEntry 6 }

    hwCesopPortPerfTable OBJECT-TYPE
      SYNTAX SEQUENCE OF HwCesopPortPerfEntry
      MAX-ACCESS not-accessible
      STATUS current
      DESCRIPTION
        "The performance statistics of the CESoP port.
         The index of this table is ifIndex.
        "
      ::= { hwCesopMibObjects 2 }

    hwCesopPortPerfEntry OBJECT-TYPE
      SYNTAX HwCesopPortPerfEntry
      MAX-ACCESS not-accessible
      STATUS current
      DESCRIPTION
        "The performance statistics of the CESoP port.
         The index of this entry is ifIndex.
        "
      INDEX { ifIndex }
      ::= { hwCesopPortPerfTable 1 }

    HwCesopPortPerfEntry ::=
      SEQUENCE
      {
        hwCesopPortPerfESs       Gauge32,
        hwCesopPortPerfSESs      Gauge32,
        hwCesopPortCurrentUASs   Gauge32
      }

    hwCesopPortPerfESs OBJECT-TYPE
      SYNTAX Gauge32(0..2147483647)
      MAX-ACCESS read-only
      STATUS current
      DESCRIPTION
        "The number of error seconds.
        "
      ::= { hwCesopPortPerfEntry 1 }

    hwCesopPortPerfSESs OBJECT-TYPE
      SYNTAX Gauge32(0..2147483647)
      MAX-ACCESS read-only
      STATUS current
      DESCRIPTION
        "The number of serious error seconds.
        "
      ::= { hwCesopPortPerfEntry 2 }

    hwCesopPortCurrentUASs OBJECT-TYPE
      SYNTAX Gauge32(0..2147483647)
      MAX-ACCESS read-only
      STATUS current
      DESCRIPTION
        "The number of unavailable seconds.
        "
      ::= { hwCesopPortPerfEntry 3 }


    hwCesopBoardCfgTable OBJECT-TYPE
      SYNTAX SEQUENCE OF HwCesopBoardCfgEntry
      MAX-ACCESS not-accessible
      STATUS current
      DESCRIPTION
        "This table is used for setting CESoP board configuration.
         The indexes of this table are hwCesopFrameIndex, hwCesopSlotIndex and hwCesopZLIndex.
        "
      ::= { hwCesopMibObjects 3 }

    hwCesopBoardCfgEntry OBJECT-TYPE
      SYNTAX HwCesopBoardCfgEntry
      MAX-ACCESS not-accessible
      STATUS current
      DESCRIPTION
        "This table is used for setting CESoP board configuration.
         The indexes of this entry are hwCesopFrameIndex, hwCesopSlotIndex and hwCesopZLIndex.
        "
      INDEX { hwCesopFrameIndex, hwCesopSlotIndex, hwCesopZLIndex }
      ::= { hwCesopBoardCfgTable 1 }

    HwCesopBoardCfgEntry ::=
      SEQUENCE
      {
        hwCesopFrameIndex                Integer32,
        hwCesopSlotIndex                 Integer32,
        hwCesopZLIndex                   Integer32,
        hwCesopBoardIpAddress            IpAddress,
        hwCesopBoardMac                  MacAddress,
        hwCesopBoardOperStatus           RowStatus,
        hwCesopBoardRecoveryClockSource  Integer32
      }

    hwCesopFrameIndex OBJECT-TYPE
      SYNTAX Integer32(0)
      MAX-ACCESS not-accessible
      STATUS current
      DESCRIPTION
        "Frame ID of the CESoP board.
         Only the value 0 is supported.
         "
      ::= { hwCesopBoardCfgEntry 1 }

    hwCesopSlotIndex OBJECT-TYPE
      SYNTAX Integer32(0..22)
      MAX-ACCESS not-accessible
      STATUS current
      DESCRIPTION
        "Slot ID of the CESoP board.
        "
      ::= { hwCesopBoardCfgEntry 2 }

    hwCesopZLIndex OBJECT-TYPE
      SYNTAX Integer32(0)
      MAX-ACCESS not-accessible
      STATUS current
      DESCRIPTION
        "ZL chip ID of the CESoP board.
         Only the value 0 is supported.
          "
      ::= { hwCesopBoardCfgEntry 3 }

    hwCesopBoardIpAddress OBJECT-TYPE
      SYNTAX IpAddress
      MAX-ACCESS read-write
      STATUS current
      DESCRIPTION
        "Ip address of the CESoP board."
      ::= { hwCesopBoardCfgEntry 4 }

    hwCesopBoardMac OBJECT-TYPE
      SYNTAX MacAddress
      MAX-ACCESS read-only
      STATUS current
      DESCRIPTION
        "Mac address of the CESoP board."
      ::= { hwCesopBoardCfgEntry 5 }

    hwCesopBoardOperStatus OBJECT-TYPE
      SYNTAX RowStatus
      MAX-ACCESS read-create
      STATUS current
      DESCRIPTION
        "The present operation status of the row.
         Options:
         1. active(1)          -the status of the row is active
         2. notInService(2)    -the status of the row is notInService
         3. notReady(3)        -the status of the row is notReady
         4. createAndGo(4)     -the status of the row is createAndGo
         5. createAndWait(5)   -the status of the row is createAndWait
         6. destroy(6)         -the status of the row is destroy
         Active(1) and notInService(2) are states, these values may be read or written.
         NotReady(3) is a state, this value may be read, but not written.
         CreateAndGo(4), createAndWait(5) and destroy(6) are actions, these values may
         be written, but are never read.
        "
      ::= { hwCesopBoardCfgEntry 6 }

    hwCesopBoardRecoveryClockSource OBJECT-TYPE
      SYNTAX Integer32(0..125)
      MAX-ACCESS read-write
      STATUS current
      DESCRIPTION
        "Recovery clock source of the CESoP board.
        "
      ::= { hwCesopBoardCfgEntry 7 }

    hwCesopConnectCfgTable OBJECT-TYPE
      SYNTAX SEQUENCE OF HwCesopConnectCfgEntry
      MAX-ACCESS not-accessible
      STATUS current
      DESCRIPTION
        "This table is used for setting CESoP link configuration.
         The index of this table is hwCesopConnectIndex.
        "
      ::= { hwCesopMibObjects 4 }

    hwCesopConnectCfgEntry OBJECT-TYPE
      SYNTAX HwCesopConnectCfgEntry
      MAX-ACCESS not-accessible
      STATUS current
      DESCRIPTION
        "This table is used for setting CESoP link configuration.
         The index of this entry is hwCesopConnectIndex.
        "
      INDEX { hwCesopConnectIndex  }
      ::= { hwCesopConnectCfgTable 1 }

    HwCesopConnectCfgEntry ::=
      SEQUENCE
      {
        hwCesopConnectIndex         Integer32,
        hwCesopConnectPortIndex     Integer32,
        hwCesopRemoteMac            MacAddress,
        hwCesopRemoteIp             IpAddress,
        hwCesopRemoteUDPPort        Integer32,
        hwCesopLocalUDPPort         Integer32,
        hwCesopVlanId               Integer32,
        hwCesopConnectRowStatus     RowStatus,
        hwCesopRTPEnable            INTEGER,
        hwCesopJitterBuffer         Integer32,
        hwCesopTDMPayloadSize       Integer32,
        hwCesopTDMLoadTime          Integer32,
        hwCesopPriority             Integer32,
        hwCesopTDMVCLIndex          Integer32,
        hwCesopRcvLSPLabel          Integer32,
        hwCesopRcvPWLabel           Integer32,
        hwCesopTransLSPLabel        Integer32,
        hwCesopTransPWLabel         Integer32,
        hwCesopGateway              IpAddress,
        hwCesopRcvSsrcId            Integer32,
        hwCesopTxSsrcId             Integer32,
        hwCesopPayloadType          Integer32,
        hwCesopSnStartNum           Integer32,
        hwCesopRemoteMacStatus      INTEGER
      }

    hwCesopConnectIndex OBJECT-TYPE
      SYNTAX Integer32(-1..2147483647)
      MAX-ACCESS not-accessible
      STATUS current
      DESCRIPTION
        "CESoP link connection id.
        "
      ::= { hwCesopConnectCfgEntry 1 }

    hwCesopConnectPortIndex OBJECT-TYPE
      SYNTAX Integer32
      MAX-ACCESS read-create
      STATUS current
      DESCRIPTION
        "The index of CESoP interface."
      ::= { hwCesopConnectCfgEntry 2 }

    hwCesopRemoteMac OBJECT-TYPE
      SYNTAX MacAddress
      MAX-ACCESS read-create
      STATUS current
      DESCRIPTION
        "The remote MAC address.
        "
      ::= { hwCesopConnectCfgEntry 3 }

    hwCesopRemoteIp OBJECT-TYPE
      SYNTAX IpAddress
      MAX-ACCESS read-create
      STATUS current
      DESCRIPTION
        "The remote CESoP port IP.
        "
      ::= { hwCesopConnectCfgEntry 4 }

    hwCesopRemoteUDPPort OBJECT-TYPE
      SYNTAX Integer32(-1..65535)
      MAX-ACCESS read-create
      STATUS current
      DESCRIPTION
        "The remote UDP label.
        "
      ::= { hwCesopConnectCfgEntry 5 }

    hwCesopLocalUDPPort OBJECT-TYPE
      SYNTAX Integer32(-1..65535)
      MAX-ACCESS read-create
      STATUS current
      DESCRIPTION
        "The local UDP label.
          "
      ::= { hwCesopConnectCfgEntry 6 }

    hwCesopVlanId OBJECT-TYPE
      SYNTAX Integer32(1..4093)
        MAX-ACCESS read-create
      STATUS current
      DESCRIPTION
        "The VlanID."
      ::= { hwCesopConnectCfgEntry 7 }

    hwCesopConnectRowStatus OBJECT-TYPE
      SYNTAX RowStatus
      MAX-ACCESS read-create
      STATUS current
      DESCRIPTION
        "The present operation status of the row.
         Options:
         1. active(1)           -the status of the row is active
         2. notInService(2)     -the status of the row is notInService
         3. notReady(3)         -the status of the row is notReady
         4. createAndGo(4)      -the status of the row is createAndGo
         5. createAndWait(5)    -the status of the row is createAndWait
         6. destroy(6)          -the status of the row is destroy
         Active(1) and notInService(2) are states, these values may be read or written.
         NotReady(3) is a state, this value may be read, but not written.
         CreateAndGo(4), createAndWait(5) and destroy(6) are actions, these values may
         be written, but are never read.
        "
      ::= { hwCesopConnectCfgEntry 8 }

    hwCesopRTPEnable OBJECT-TYPE
      SYNTAX INTEGER
        {
        disable(1),
        enable(2)
        }
      MAX-ACCESS read-create
      STATUS current
      DESCRIPTION
        "The RTP switch of CESoP link.
         Options:
         1. disable(1)  -the RTP switch of CESoP link is disable
         2. enable(2)   -the RTP switch of CESoP link is enable
        "
      DEFVAL {enable}
      ::= { hwCesopConnectCfgEntry 9 }

    hwCesopJitterBuffer OBJECT-TYPE
      SYNTAX Integer32(500..32000)
      MAX-ACCESS read-create
      STATUS current
      DESCRIPTION
        "The jitterBuffer size of CESoP link.
        "
      DEFVAL {2000}
      ::= { hwCesopConnectCfgEntry 10 }

    hwCesopTDMPayloadSize OBJECT-TYPE
      SYNTAX Integer32(32..768)
      MAX-ACCESS read-create
      STATUS current
      DESCRIPTION
        "
       The length of CESoP packets payload.
       +-+-+-+-+-+-+-+-+-+-+-+-+-+-+-+-+-+-+-+-+-+-+-+-+-+-+-+-+-+-+-+-+
       |                           ...                                 |
       |                   IPv4/IPv6 and UDP headers                   |
       |                           ...                                 |
       +=+=+=+=+=+=+=+=+=+=+=+=+=+=+=+=+=+=+=+=+=+=+=+=+=+=+=+=+=+=+=+=+
       |                       OPTIONAL                                |
       +--                                                           --+
       |                                                               |
       +--                                                           --+
       |                 Fixed RTP Header (see [RFC3550])              |
       +=+=+=+=+=+=+=+=+=+=+=+=+=+=+=+=+=+=+=+=+=+=+=+=+=+=+=+=+=+=+=+=+
       |                  CESoPSN Control Word                         |
       +=+=+=+=+=+=+=+=+=+=+=+=+=+=+=+=+=+=+=+=+=+=+=+=+=+=+=+=+=+=+=+=+
       |                Packetized TDM data (Payload)                  |
       |                            ...                                |
       |                            ...                                |
       +-+-+-+-+-+-+-+-+-+-+-+-+-+-+-+-+-+-+-+-+-+-+-+-+-+-+-+-+-+-+-+-+.

       The length of payload must be multiple of 32."
      DEFVAL {256}
      ::= { hwCesopConnectCfgEntry 11 }


      hwCesopTDMLoadTime OBJECT-TYPE
      SYNTAX Integer32(125..5000)
      MAX-ACCESS read-create
      STATUS current
      DESCRIPTION
      "The TDM LoadTime of CESoP link, it must be a multiple of 125. If the entered value is not a multiple of 125,
      the system rounds it down to the nearest multiple of 125. The value of this field must be equal to or lower
      than the jitterBuffer size of the same CESoP link. The unit of this field is microsecond(us).
      "
      DEFVAL {125}
      ::= { hwCesopConnectCfgEntry 12 }

      hwCesopPriority OBJECT-TYPE
      SYNTAX Integer32(0..7)
      MAX-ACCESS read-create
      STATUS current
      DESCRIPTION
      "The Priority of CESoP link"
      DEFVAL {7}
      ::= { hwCesopConnectCfgEntry 13 }

      hwCesopTDMVCLIndex OBJECT-TYPE
      SYNTAX Integer32(-1..65535)
      MAX-ACCESS read-create
      STATUS current
      DESCRIPTION
      "TDM-VCL ID"
      ::= { hwCesopConnectCfgEntry 14 }

      hwCesopRcvLSPLabel OBJECT-TYPE
      SYNTAX Integer32(-1 | 8192..8447)
      MAX-ACCESS read-create
      STATUS current
      DESCRIPTION
      "The LSP label of received packet."
      ::= { hwCesopConnectCfgEntry 15 }

      hwCesopRcvPWLabel OBJECT-TYPE
      SYNTAX Integer32(-1 | 8448..8703)
      MAX-ACCESS read-create
      STATUS current
      DESCRIPTION
      "The PW label of received packet."
      ::= { hwCesopConnectCfgEntry 16 }

      hwCesopTransLSPLabel OBJECT-TYPE
      SYNTAX Integer32(-1 | 16..1048575)
      MAX-ACCESS read-create
      STATUS current
      DESCRIPTION
      "The LSP label of transmitted packet."
      ::= { hwCesopConnectCfgEntry 17 }

      hwCesopTransPWLabel OBJECT-TYPE
      SYNTAX Integer32(-1 | 16..1048575)
      MAX-ACCESS read-create
      STATUS current
      DESCRIPTION
      "The PW label of transmitted packet."
      ::= { hwCesopConnectCfgEntry 18 }

    hwCesopGateway OBJECT-TYPE
      SYNTAX IpAddress
      MAX-ACCESS read-create
      STATUS current
      DESCRIPTION
        "The gateway IP address.
        "
      ::= { hwCesopConnectCfgEntry 19 }

    hwCesopRcvSsrcId OBJECT-TYPE
      SYNTAX Integer32
      MAX-ACCESS read-create
      STATUS current
      DESCRIPTION
      "The recieve SSRC ID in RTP header.
      "
      ::= { hwCesopConnectCfgEntry 20 }

    hwCesopTxSsrcId OBJECT-TYPE
      SYNTAX Integer32
      MAX-ACCESS read-create
      STATUS current
      DESCRIPTION
      "The transmit SSRC ID in RTP header.
      "
      ::= { hwCesopConnectCfgEntry 21 }

    hwCesopPayloadType OBJECT-TYPE
      SYNTAX Integer32
      MAX-ACCESS read-create
      STATUS current
      DESCRIPTION
      "The payload type in RTP header.
      "
      ::= { hwCesopConnectCfgEntry 22 }

    hwCesopSnStartNum OBJECT-TYPE
      SYNTAX Integer32(0..1)
      MAX-ACCESS read-create
      STATUS current
      DESCRIPTION
      "The sn start number in RTP header.
      "
      ::= { hwCesopConnectCfgEntry 23 }

    hwCesopRemoteMacStatus OBJECT-TYPE
      SYNTAX INTEGER
      {
        static(1),
        resolving(2),
        resolved(3),
        aged(4)
      }
      MAX-ACCESS read-only
      STATUS current
      DESCRIPTION
        "The remote MAC address resolving status.
         Options:
         1. static(1)    -the remote MAC address is configured by user.
         2. resolving(2) -the remote MAC address has not beed resolved.
         3. resolved(3)  -the remote MAC address has been resolved.
         4. aged(4)      -the remote MAC address has been aged.
        "
      ::= { hwCesopConnectCfgEntry 24 }

    hwCesopGlobalPerfTable OBJECT-TYPE
      SYNTAX SEQUENCE OF HwCesopGlobalPerfEntry
      MAX-ACCESS not-accessible
      STATUS current
      DESCRIPTION
        "The table of CESoP global performance statistics.
         The indexes of this table are hwCesopPerfFrameIndex and hwCesopPerfBoardIndex.
        "
      ::= { hwCesopMibObjects 5 }

    hwCesopGlobalPerfEntry OBJECT-TYPE
      SYNTAX HwCesopGlobalPerfEntry
      MAX-ACCESS not-accessible
      STATUS current
      DESCRIPTION
        "The table of CESoP global performance statistics.
         The indexes of this entry are hwCesopPerfFrameIndex and hwCesopPerfBoardIndex.
        "
      INDEX { hwCesopPerfFrameIndex, hwCesopPerfBoardIndex }
      ::= { hwCesopGlobalPerfTable 1 }

    HwCesopGlobalPerfEntry ::=
      SEQUENCE
       {
        hwCesopPerfFrameIndex
                Integer32,
        hwCesopPerfBoardIndex
                Integer32,
        hwCesopProtocolStackMatchCountH
                Counter64,
        hwCesopProtocolStackMatchCountL
                Counter64,
        hwCesopProtocolStackNoMatchCount
                Counter32,
        hwCesopClassifyNoMatchCount
                Counter32,
        hwCesopVerificationFailureCount
                Counter32,
        hwCesopIPv4ChecksumFailureCount
                Counter32,
        hwCesopUDPChecksumFailureCount
                Counter32,
        hwCesopDropEvents
                Counter64,
        hwCesopBytesReceived
                Counter64,
        hwCesopFramesReceived
                Counter64,
        hwCesopBroadcastPacketsReceived
                Counter64,
        hwCesopMulticastPacketsReceived
                Counter64,
        hwCesopCRCAlignmentErrorsReceived
                Counter64,
        hwCesopUndersizedFramesReceived
                Counter64,
        hwCesopOversizedPacketsReceived
                Counter64,
        hwCesopFragmentsReceived
                Counter64,
        hwCesopJabberFramesReceived
                Counter64,
        hwCesopConflictFramesReceived
                Counter64,
        hwCesopPacketsOfLength64Received
                Counter64,
        hwCesopPacketsOfLength65To127Received
                Counter64,
        hwCesopPacketsOfLength128To255Received
                Counter64,
        hwCesopPacketsOfLength256To511Received
                Counter64,
        hwCesopPacketsOfLength512To1023Received
                Counter64,
        hwCesopPacketsOfLength1024To1518Received
                Counter64,
        hwCesopOctetsReceived
                Counter64,
        hwCesopUnicastPacketsReceived
                Counter64,
        hwCesopMulticastAndBroadcastPacketsReceived
                Counter64,
        hwCesopDiscardedPacketsInBound
                Counter64,
        hwCesopErroredPacketsReceived
                Counter64,
        hwCesopUnknownProtocolPacketsReceived
                Counter64,
        hwCesopOctetsTransmitted
                Counter64,
        hwCesopUnicastPacketsTransmitted
                Counter64,
        hwCesopMulticastAndBroadcastPacketsTransmitted
                Counter64,
        hwCesopDiscardedPacketsOutbound
                Counter32,
        hwCesopErroredPacketsOutbound
                Counter64,
        hwCesopLengthOfTheOutboundPacketQueue
                Counter32,
        hwCesopDmacErrorsReceived
                Counter64,
        hwCesopDipErrorsReceived
                Counter64,
        hwCesopDPortErrorsReceived
                Counter64,
        hwCesopFramesTransmitted
                Counter64,
        hwCesopGlobalPerfClearStat
                INTEGER
       }

    hwCesopPerfFrameIndex OBJECT-TYPE
      SYNTAX Integer32(0)
      MAX-ACCESS not-accessible
      STATUS current
      DESCRIPTION
        "Frame ID of the statistics CESoP board.
         Only the value 0 is supported.
         "
      ::= { hwCesopGlobalPerfEntry 1 }

    hwCesopPerfBoardIndex OBJECT-TYPE
      SYNTAX Integer32(0..22)
      MAX-ACCESS not-accessible
      STATUS current
      DESCRIPTION
        "Slot ID of the statistics CESoP board.
        "
      ::= { hwCesopGlobalPerfEntry 2 }


    hwCesopProtocolStackMatchCountH OBJECT-TYPE
      SYNTAX Counter64
      MAX-ACCESS read-only
      STATUS current
      DESCRIPTION
        "The high byte of the match protocol packets counter.
        "
      ::= { hwCesopGlobalPerfEntry 3 }

    hwCesopProtocolStackMatchCountL OBJECT-TYPE
      SYNTAX Counter64
      MAX-ACCESS read-only
      STATUS current
      DESCRIPTION
        "The low byte of the match protocol packets counter.
        "
      ::= { hwCesopGlobalPerfEntry 4 }

    hwCesopProtocolStackNoMatchCount OBJECT-TYPE
      SYNTAX Counter32
      MAX-ACCESS read-only
      STATUS current
      DESCRIPTION
        "The number of mismatch protocol packets.
        "
      ::= { hwCesopGlobalPerfEntry 5 }

    hwCesopClassifyNoMatchCount OBJECT-TYPE
      SYNTAX Counter32
      MAX-ACCESS read-only
      STATUS current
      DESCRIPTION
        "The number of mismatch classify rules packets.
        "
      ::= { hwCesopGlobalPerfEntry 6 }


    hwCesopVerificationFailureCount OBJECT-TYPE
      SYNTAX Counter32
      MAX-ACCESS read-only
      STATUS current
      DESCRIPTION
        "The number of verification failure packets.
        "
      ::= { hwCesopGlobalPerfEntry 7 }

    hwCesopIPv4ChecksumFailureCount OBJECT-TYPE
      SYNTAX Counter32
      MAX-ACCESS read-only
      STATUS current
      DESCRIPTION
        "The number of IP check sum failure packets.
        "
      ::= { hwCesopGlobalPerfEntry 8 }

    hwCesopUDPChecksumFailureCount OBJECT-TYPE
      SYNTAX Counter32
      MAX-ACCESS read-only
      STATUS current
      DESCRIPTION
        "The number of UDP check sum failure packets.
        "
      ::= { hwCesopGlobalPerfEntry 9 }

    hwCesopDropEvents OBJECT-TYPE
      SYNTAX Counter64
      MAX-ACCESS read-only
      STATUS current
      DESCRIPTION
        "The number of dropped events.
        "
      ::= { hwCesopGlobalPerfEntry 10 }

    hwCesopBytesReceived OBJECT-TYPE
      SYNTAX Counter64
      MAX-ACCESS read-only
      STATUS current
      DESCRIPTION
        "The number of received bytes.
        "
      ::= { hwCesopGlobalPerfEntry 11 }

    hwCesopFramesReceived OBJECT-TYPE
      SYNTAX Counter64
      MAX-ACCESS read-only
      STATUS current
      DESCRIPTION
        "The number of received frames.
        "
      ::= { hwCesopGlobalPerfEntry 12 }

    hwCesopBroadcastPacketsReceived OBJECT-TYPE
      SYNTAX Counter64
      MAX-ACCESS read-only
      STATUS current
      DESCRIPTION
        "The number of received broadcast frames.
        "
      ::= { hwCesopGlobalPerfEntry 13 }

    hwCesopMulticastPacketsReceived OBJECT-TYPE
      SYNTAX Counter64
      MAX-ACCESS read-only
      STATUS current
      DESCRIPTION
        "The number of received multicast frames.
        "
      ::= { hwCesopGlobalPerfEntry 14 }

    hwCesopCRCAlignmentErrorsReceived OBJECT-TYPE
      SYNTAX Counter64
      MAX-ACCESS read-only
      STATUS current
      DESCRIPTION
        "The number of received CRC errors packets.
        "
      ::= { hwCesopGlobalPerfEntry 15 }

    hwCesopUndersizedFramesReceived OBJECT-TYPE
      SYNTAX Counter64
      MAX-ACCESS read-only
      STATUS current
      DESCRIPTION
        "The number of received undersized frames.
        "
      ::= { hwCesopGlobalPerfEntry 16 }

    hwCesopOversizedPacketsReceived OBJECT-TYPE
      SYNTAX Counter64
      MAX-ACCESS read-only
      STATUS current
      DESCRIPTION
        "The number of received oversized frames.
        "
      ::= { hwCesopGlobalPerfEntry 17 }

    hwCesopFragmentsReceived OBJECT-TYPE
      SYNTAX Counter64
      MAX-ACCESS read-only
      STATUS current
      DESCRIPTION
        "The number of received fragments.
          "
      ::= { hwCesopGlobalPerfEntry 18 }

    hwCesopJabberFramesReceived OBJECT-TYPE
      SYNTAX Counter64
      MAX-ACCESS read-only
      STATUS current
      DESCRIPTION
        "The number of received jabber frames.
        "
      ::= { hwCesopGlobalPerfEntry 19 }

    hwCesopConflictFramesReceived OBJECT-TYPE
      SYNTAX Counter64
      MAX-ACCESS read-only
      STATUS current
      DESCRIPTION
        "The number of received conflict frames.
        "
      ::= { hwCesopGlobalPerfEntry 20 }

    hwCesopPacketsOfLength64Received OBJECT-TYPE
      SYNTAX Counter64
      MAX-ACCESS read-only
      STATUS current
      DESCRIPTION
        "The number of received 64-byte frames.
        "
      ::= { hwCesopGlobalPerfEntry 21 }

    hwCesopPacketsOfLength65To127Received OBJECT-TYPE
      SYNTAX Counter64
      MAX-ACCESS read-only
      STATUS current
      DESCRIPTION
        "The number of received 65~127-byte frames.
        "
      ::= { hwCesopGlobalPerfEntry 22 }

    hwCesopPacketsOfLength128To255Received OBJECT-TYPE
      SYNTAX Counter64
      MAX-ACCESS read-only
      STATUS current
      DESCRIPTION
        "The number of received 128~255-byte frames.
        "
      ::= { hwCesopGlobalPerfEntry 23 }

    hwCesopPacketsOfLength256To511Received OBJECT-TYPE
      SYNTAX Counter64
      MAX-ACCESS read-only
      STATUS current
      DESCRIPTION
        "The number of received 256~511-byte frames.
        "
      ::= { hwCesopGlobalPerfEntry 24 }

    hwCesopPacketsOfLength512To1023Received OBJECT-TYPE
      SYNTAX Counter64
      MAX-ACCESS read-only
      STATUS current
      DESCRIPTION
        "The number of received 512~1023-byte frames.
        "
      ::= { hwCesopGlobalPerfEntry 25 }

    hwCesopPacketsOfLength1024To1518Received OBJECT-TYPE
      SYNTAX Counter64
      MAX-ACCESS read-only
      STATUS current
      DESCRIPTION
        "The number of received 1024~1518-byte frames.
        "
      ::= { hwCesopGlobalPerfEntry 26 }

    hwCesopOctetsReceived OBJECT-TYPE
      SYNTAX Counter64
      MAX-ACCESS read-only
      STATUS current
      DESCRIPTION
        "The number of received bytes.
        "
      ::= { hwCesopGlobalPerfEntry 27 }

    hwCesopUnicastPacketsReceived OBJECT-TYPE
      SYNTAX Counter64
      MAX-ACCESS read-only
      STATUS current
      DESCRIPTION
        "The number of received unicast packets.
        "
      ::= { hwCesopGlobalPerfEntry 28 }

    hwCesopMulticastAndBroadcastPacketsReceived OBJECT-TYPE
      SYNTAX Counter64
      MAX-ACCESS read-only
      STATUS current
      DESCRIPTION
        "The number of received multicast and broadcast packets.
        "
      ::= { hwCesopGlobalPerfEntry 29 }

    hwCesopDiscardedPacketsInBound OBJECT-TYPE
      SYNTAX Counter64
      MAX-ACCESS read-only
      STATUS current
      DESCRIPTION
        "The number of received discarded packets.
        "
      ::= { hwCesopGlobalPerfEntry 30 }

    hwCesopErroredPacketsReceived OBJECT-TYPE
      SYNTAX Counter64
      MAX-ACCESS read-only
      STATUS current
      DESCRIPTION
        "The number of received errored packets.
        "
      ::= { hwCesopGlobalPerfEntry 31 }

    hwCesopUnknownProtocolPacketsReceived OBJECT-TYPE
      SYNTAX Counter64
      MAX-ACCESS read-only
      STATUS current
      DESCRIPTION
        "The number of received unknown protocol packets.
        "
      ::= { hwCesopGlobalPerfEntry 32 }

    hwCesopOctetsTransmitted OBJECT-TYPE
      SYNTAX Counter64
      MAX-ACCESS read-only
      STATUS current
      DESCRIPTION
        "The number of transmitted bytes.
        "
      ::= { hwCesopGlobalPerfEntry 33 }

    hwCesopUnicastPacketsTransmitted OBJECT-TYPE
      SYNTAX Counter64
      MAX-ACCESS read-only
      STATUS current
      DESCRIPTION
        "The number of transmitted unicast packets.
        "
      ::= { hwCesopGlobalPerfEntry 34 }

    hwCesopMulticastAndBroadcastPacketsTransmitted OBJECT-TYPE
      SYNTAX Counter64
      MAX-ACCESS read-only
      STATUS current
      DESCRIPTION
        "The number of transmitted multicast and broadcast packets.
        "
      ::= { hwCesopGlobalPerfEntry 35 }

    hwCesopDiscardedPacketsOutbound OBJECT-TYPE
      SYNTAX Counter32
      MAX-ACCESS read-only
      STATUS current
      DESCRIPTION
        "The number of transmitted discarded packets.
        "
      ::= { hwCesopGlobalPerfEntry 36 }

    hwCesopErroredPacketsOutbound OBJECT-TYPE
      SYNTAX Counter64
      MAX-ACCESS read-only
      STATUS current
      DESCRIPTION
        "The number of transmitted errored packets.
        "
      ::= { hwCesopGlobalPerfEntry 37 }

    hwCesopLengthOfTheOutboundPacketQueue OBJECT-TYPE
      SYNTAX Counter32
      MAX-ACCESS read-only
      STATUS current
      DESCRIPTION
        "The length of transmitted packets queues.
        "
      ::= { hwCesopGlobalPerfEntry 38 }

    hwCesopDmacErrorsReceived OBJECT-TYPE
      SYNTAX Counter64
      MAX-ACCESS read-only
      STATUS current
      DESCRIPTION
        "The number of destination MAC error packets.
        "
      ::= { hwCesopGlobalPerfEntry 39 }

    hwCesopDipErrorsReceived OBJECT-TYPE
      SYNTAX Counter64
      MAX-ACCESS read-only
      STATUS current
      DESCRIPTION
        "The number of destination IP error packets.
        "
      ::= { hwCesopGlobalPerfEntry 40 }

    hwCesopDPortErrorsReceived OBJECT-TYPE
      SYNTAX Counter64
      MAX-ACCESS read-only
      STATUS current
      DESCRIPTION
        "The number of destination UDP port error packets.
        "
      ::= { hwCesopGlobalPerfEntry 41 }

    hwCesopFramesTransmitted OBJECT-TYPE
      SYNTAX Counter64
      MAX-ACCESS read-only
      STATUS current
      DESCRIPTION
        "The number of transmitted packets.
        "
      ::= { hwCesopGlobalPerfEntry 42 }

    hwCesopGlobalPerfClearStat OBJECT-TYPE
      SYNTAX INTEGER
      {
      clear(1)
      }
      MAX-ACCESS read-write
      STATUS current
      DESCRIPTION
        "Clear statistics information of the CESoP board.
         Options:
         1. clear(1)         -clear statistics information of the CESoP board
         "
      DEFVAL {clear}
      ::= { hwCesopGlobalPerfEntry 43 }

    hwCesopConnectPerfTable OBJECT-TYPE
      SYNTAX SEQUENCE OF HwCesopConnectPerfEntry
      MAX-ACCESS not-accessible
      STATUS current
      DESCRIPTION
        "The table of CESoP connection performance statistics.
         The index of this table is hwCesopPerfConnectPwID.
        "
      ::= { hwCesopMibObjects 6 }

    hwCesopConnectPerfEntry OBJECT-TYPE
      SYNTAX HwCesopConnectPerfEntry
      MAX-ACCESS not-accessible
      STATUS current
      DESCRIPTION
        "The table of CESoP connection performance statistics.
         The index of this entry is hwCesopPerfConnectPwID.
        "
      INDEX { hwCesopPerfConnectPwID }
      ::= { hwCesopConnectPerfTable 1 }

    HwCesopConnectPerfEntry ::=
      SEQUENCE {
        hwCesopPerfConnectPwID
                Integer32,
        hwCesopConnectEarlyPackets
                Counter32,
        hwCesopConnectLatePackets
                Counter32,
        hwCesopConnectUnderrunPackets
                Counter32,
        hwCesopConnectLostPackets
                Counter32,
        hwCesopConnectCurrentQueueLength
                Counter32,
        hwCesopConnectAverageQueueLength
                Counter32,
        hwCesopConnectMaximumQueueLength
                Counter32,
        hwCesopConnectMinimumQueueLength
                Counter32,
        hwCesopConnectPacketReceiveCount
                Counter32,
        hwCesopConnectPacketTransmitCount
                Counter32,
        hwCesopConnectByteTransmitCount
                Counter32,
        hwCesopConnectLBitCount
                Counter32,
        hwCesopConnectLBitSetTime
                Counter32,
        hwCesopConnectRBitCount
                Counter32,
        hwCesopConnectRBitSetTime
                Counter32,
        hwCesopConnectBufOverRunCount
                Counter32,
        hwCesopConnectBufOverRunSetTime
                Counter32,
        hwCesopConnectBufUnderRunCount
                Counter32,
        hwCesopConnectUnderRunSetTime
                Counter32,
        hwCesopConnectPerfClearStat
                INTEGER,
        hwCesopConnectChannelInPkts
                Counter32,
        hwCesopConnectChannelOutPkts
                Counter32,
        hwCesopConnectChannelInSequenceErrors
                Counter32,
        hwCesopConnectChannelInVlanInvalid
                Counter32,
        hwCesopQueueUnderflow
                Counter32,
        hwCesopQueueOverflow
                Counter32,
        hwCesopConnectPacketReceiveErrorCount
                Counter32,
        hwCesopConnectPacketReceiveSSrcErrorCount
                Counter32
       }

    hwCesopPerfConnectPwID OBJECT-TYPE
      SYNTAX Integer32(0..2147483647)
      MAX-ACCESS not-accessible
      STATUS current
      DESCRIPTION
        "The CESoP link ID of performance statistics.
        "
      ::= { hwCesopConnectPerfEntry 1 }

    hwCesopConnectEarlyPackets OBJECT-TYPE
      SYNTAX Counter32
      MAX-ACCESS read-only
      STATUS current
      DESCRIPTION
        "Early packets number of the CESoP link.
        "
      ::= { hwCesopConnectPerfEntry 2 }

    hwCesopConnectLatePackets OBJECT-TYPE
      SYNTAX Counter32
      MAX-ACCESS read-only
      STATUS current
      DESCRIPTION
        "Late packets number of the CESoP link.
        "
      ::= { hwCesopConnectPerfEntry 3 }

    hwCesopConnectUnderrunPackets OBJECT-TYPE
      SYNTAX Counter32
      MAX-ACCESS read-only
      STATUS current
      DESCRIPTION
        "Underrun packets number of the CESoP link.
        "
      ::= { hwCesopConnectPerfEntry 4 }

    hwCesopConnectLostPackets OBJECT-TYPE
      SYNTAX Counter32
      MAX-ACCESS read-only
      STATUS current
      DESCRIPTION
        "Lost packets number of the CESoP link.
        "
      ::= { hwCesopConnectPerfEntry 5 }

    hwCesopConnectCurrentQueueLength OBJECT-TYPE
      SYNTAX Counter32
      MAX-ACCESS read-only
      STATUS current
      DESCRIPTION
        "Current queue length of the CESoP link.
        "
      ::= { hwCesopConnectPerfEntry 6 }

    hwCesopConnectAverageQueueLength OBJECT-TYPE
      SYNTAX Counter32
      MAX-ACCESS read-only
      STATUS current
      DESCRIPTION
        "Average queue length of the CESoP link."
      ::= { hwCesopConnectPerfEntry 7 }

    hwCesopConnectMaximumQueueLength OBJECT-TYPE
      SYNTAX Counter32
      MAX-ACCESS read-only
      STATUS current
      DESCRIPTION
        "Maximum queue length of the CESoP link.
        "
      ::= { hwCesopConnectPerfEntry 8 }

    hwCesopConnectMinimumQueueLength OBJECT-TYPE
      SYNTAX Counter32
      MAX-ACCESS read-only
      STATUS current
      DESCRIPTION
        "Minimum queue length of the CESoP link.
        "
      ::= { hwCesopConnectPerfEntry 9 }

    hwCesopConnectPacketReceiveCount OBJECT-TYPE
      SYNTAX Counter32
      MAX-ACCESS read-only
      STATUS current
      DESCRIPTION
        "Received packets number of the CESoP link.
        "
      ::= { hwCesopConnectPerfEntry 10 }

    hwCesopConnectPacketTransmitCount OBJECT-TYPE
      SYNTAX Counter32
      MAX-ACCESS read-only
      STATUS current
      DESCRIPTION
        "Transmitted packets number of the CESoP link."
      ::= { hwCesopConnectPerfEntry 11 }

    hwCesopConnectByteTransmitCount OBJECT-TYPE
      SYNTAX Counter32
      MAX-ACCESS read-only
      STATUS current
      DESCRIPTION
        "Transmitted bytes number of the CESoP link.
        "
      ::= { hwCesopConnectPerfEntry 12 }

    hwCesopConnectLBitCount OBJECT-TYPE
      SYNTAX Counter32
      MAX-ACCESS read-only
      STATUS current
      DESCRIPTION
        "L bit status changed number of the CESoP link."
      ::= { hwCesopConnectPerfEntry 13 }

    hwCesopConnectLBitSetTime OBJECT-TYPE
      SYNTAX Counter32
      MAX-ACCESS read-only
      STATUS current
      DESCRIPTION
        "L bit set number of the CESoP link."
      ::= { hwCesopConnectPerfEntry 14 }

    hwCesopConnectRBitCount OBJECT-TYPE
      SYNTAX Counter32
      MAX-ACCESS read-only
      STATUS current
      DESCRIPTION
        "R bit status changed number of the CESoP link.
          "
      ::= { hwCesopConnectPerfEntry 15 }

    hwCesopConnectRBitSetTime OBJECT-TYPE
      SYNTAX Counter32
      MAX-ACCESS read-only
      STATUS current
      DESCRIPTION
        "L bit set number of the CESoP link.
        "
      ::= { hwCesopConnectPerfEntry 16 }

    hwCesopConnectBufOverRunCount OBJECT-TYPE
      SYNTAX Counter32
      MAX-ACCESS read-only
      STATUS current
      DESCRIPTION
        "JitterBuffer overflow number of the CESoP link."
      ::= { hwCesopConnectPerfEntry 17 }

    hwCesopConnectBufOverRunSetTime OBJECT-TYPE
      SYNTAX Counter32
      MAX-ACCESS read-only
      STATUS current
      DESCRIPTION
        "JitterBuffer overflow reset number of the CESoP link."
      ::= { hwCesopConnectPerfEntry 18 }

    hwCesopConnectBufUnderRunCount OBJECT-TYPE
      SYNTAX Counter32
      MAX-ACCESS read-only
      STATUS current
      DESCRIPTION
        "JitterBuffer underflow number of the CESoP link.
        "
      ::= { hwCesopConnectPerfEntry 19 }

    hwCesopConnectUnderRunSetTime OBJECT-TYPE
      SYNTAX Counter32
      MAX-ACCESS read-only
      STATUS current
      DESCRIPTION
        "JitterBuffer underflow reset number of the CESoP link.
        "
      ::= { hwCesopConnectPerfEntry 20 }

    hwCesopConnectPerfClearStat OBJECT-TYPE
      SYNTAX INTEGER
      {
         clear(1),
         invalid(-1)
      }
      MAX-ACCESS read-write
      STATUS current
      DESCRIPTION
        "Clear statistics information of the CESoP link.
         Options:
         1. clear(1)         -clear statistics information of the CESoP link
         2. invalid(-1)      -invalid value
         "
      DEFVAL {clear}
      ::= { hwCesopConnectPerfEntry 21 }

    hwCesopConnectChannelInPkts OBJECT-TYPE
      SYNTAX Counter32
      MAX-ACCESS read-only
      STATUS current
      DESCRIPTION
        "Statistics of the packets received on an E1 channel.
        "
      ::= { hwCesopConnectPerfEntry 22 }

    hwCesopConnectChannelOutPkts OBJECT-TYPE
      SYNTAX Counter32
      MAX-ACCESS read-only
      STATUS current
      DESCRIPTION
        "Statistics of the packets transmitted from an E1 channel.
        "
      ::= { hwCesopConnectPerfEntry 23 }

    hwCesopConnectChannelInSequenceErrors OBJECT-TYPE
      SYNTAX Counter32
      MAX-ACCESS read-only
      STATUS current
      DESCRIPTION
        "Statistics of the SN-error packets received on an E1 channel.
        "
      ::= { hwCesopConnectPerfEntry 24 }

    hwCesopConnectChannelInVlanInvalid OBJECT-TYPE
      SYNTAX Counter32
      MAX-ACCESS read-only
      STATUS current
      DESCRIPTION
        "Statistics of the VLAN ID-error packets received on an E1 channel.
        "
      ::= { hwCesopConnectPerfEntry 25 }

    hwCesopQueueUnderflow OBJECT-TYPE
      SYNTAX Counter32
      MAX-ACCESS read-only
      STATUS current
      DESCRIPTION
        "Statistics of the packets that are dropped due to queue overflow of an E1 channel.
        "
      ::= { hwCesopConnectPerfEntry 26 }

    hwCesopQueueOverflow OBJECT-TYPE
      SYNTAX Counter32
      MAX-ACCESS read-only
      STATUS current
      DESCRIPTION
        "Statistics of the packets that are dropped due to queue underflow of an E1 channel.
        "
      ::= { hwCesopConnectPerfEntry 27 }

    hwCesopConnectPacketReceiveErrorCount OBJECT-TYPE
      SYNTAX Counter32
      MAX-ACCESS read-only
      STATUS current
      DESCRIPTION
        "Statistics of the error packets received on an E1 channel.
        "
      ::= { hwCesopConnectPerfEntry 28 }

    hwCesopConnectPacketReceiveSSrcErrorCount OBJECT-TYPE
      SYNTAX Counter32
      MAX-ACCESS read-only
      STATUS current
      DESCRIPTION
        "Statistics of the SSRC-error packets received on an E1 channel.
        "
      ::= { hwCesopConnectPerfEntry 29 }

  END
