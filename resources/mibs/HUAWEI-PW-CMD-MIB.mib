--  =================================================================
-- Copyright (C) 2013 by  HUAWEI TECHNOLOGIES. All rights reserved.
-- Description:    Pseudo Wire Emulation Edge-to-Edge (PWE3) is an end-to-end L2 service bearing technology, 
--                 that belongs to L2 VPN in the P2P mode. The system implements the PWE3 architecture through MPLS, by 
--                 using the LDP or RSVP-TE protocol as signaling. Therefore, it can implement the ATM and Ethernet emulation 
--                 services and establish the ATM or Ethernet private lines. Thus, it provides a solution to the emulation private 
--                 line service in the IP network.
-- Reference:
-- Version: V1.32
-- =================================================================
    HUAWEI-PW-CMD-MIB DEFINITIONS ::= BEGIN
 
        IMPORTS 
            hwMpls            
                FROM HUAWEI-MIB 
            ifIndex, InterfaceIndex            
                FROM IF-MIB            
            InetAddressType            
                FROM INET-ADDRESS-MIB
            IpAddress, Integer32, Unsigned32, Counter32, Counter64, 
            OBJECT-TYPE, MODULE-IDENTITY, NOTIFICATION-TYPE 
                FROM SNMPv2-SMI             
            TruthValue, TimeStamp, RowStatus, TEXTUAL-CONVENTION      
                FROM SNMPv2-TC 
            OBJECT-GROUP, NOTIFICATION-GROUP            
                FROM SNMPv2-CONF
            PwVcType
                FROM HUAWEI-PW-TC-MIB
            pwIndex, pwType, pwID, pwPeerAddrType, pwPeerAddr     -- [RFC5601]
                FROM PW-STD-MIB;
    
        hwPwCmdMIB MODULE-IDENTITY 

            LAST-UPDATED "201303200000Z"        
            ORGANIZATION "Huawei Technologies Co.,Ltd."
            CONTACT-INFO                                    
                "Huawei Industrial Base
                 Bantian, Longgang
                 Shenzhen 518129
                 People's Republic of China
                 Website: http://www.huawei.com
                 Email: support@huawei.com
                "                                  
            DESCRIPTION 
                "Pseudo Wire Emulation Edge-to-Edge (PWE3) is an end-to-end L2 service bearing technology, 
                 that belongs to L2 VPN in the P2P mode. The system implements the PWE3 architecture through MPLS, by 
                 using the LDP or RSVP-TE protocol as signaling. Therefore, it can implement the ATM and Ethernet emulation 
                 services and establish the ATM or Ethernet private lines. Thus, it provides a solution to the emulation private 
                 line service in the IP network.
                "
                
                --  Revision history
                
                REVISION    "201303200000Z"
                DESCRIPTION "V1.32, deleted obsolete node hwPwCmdNonIfGroup.
                             modified the default value of leaf node hwPwRcvSsrcId and hwPwTxSsrcId."
                
                REVISION    "201210120000Z"
                DESCRIPTION "V1.31, added leaf nodes hwPwPayloadType, hwPwSnStartNum, hwPwRcvSsrcId and hwPwTxSsrcId in table hwPwExtTable."

                REVISION    "201204110000Z"
                DESCRIPTION "V1.30, added the default value of leaf node hwPwCmdVccvReplyMode, hwPwCmdVccvFrequency, hwPwCmdVccvTimeoutLimit, hwPwCmdVccvRecoverLimit.
                             Added leaf node hwPwTnlPolicy.Added table hwPwCmdPwCarExtTable and hwPwAutoVccvTable."

                REVISION    "201109090000Z"
                DESCRIPTION "V1.29, modified the description of leaf node hwPwCmdVccvRemotePwVcID and hwPwCmdVccvTtl."
                              
                REVISION    "201107130000Z"
                DESCRIPTION "V1.28, added table hwPwPriMappingTable.                            
                            Added table hwPwRedundancyTable.
                            Added table hwPwCmdStatisticTable.
                            Modified value range of leaf node hwPwCmdPWCarCir and hwPwCmdPWCarPir, hwPwCmdRecoverVcID, hwPwCmdManualSwitchoverVcID, hwPwCmdVccvVcID, hwPwCmdVccvRemotePwVcID.
                            Modified the Max access of leaf node hwPwCmdPWCarVcID, hwPwCmdPsPwId, hwPwCmdManualSwitchoverVcID, hwPwCmdRecoverVcID.
                            Added leaf node hwPwPriMappingProfName in table hwPwExtTable to modify QoS profile for PW.
                            Added leaf node hwPwStatisticSwitch in table hwPwExtTable to configure PW statistic switch.
                            Deleted IMPORTS PwIndexType to solve mib browser compiling warning.
                            Modified HwPwExtTableEntry to HwPwExtEntry and hwPwExtTableEntry to hwPwExtEntry for MIB browser compiling warning.
                            Added leaf node hwPwFlowLabelCapabilities and hwPwFlowlabelStatus in table hwPwExtTable to modify FlowLabel for Ethernet PW.
                            Added leaf node hwPwCmdVccvPingPipeUniform in table hwPwCmdVccvTable for setting VCCV ping mode."                          

                REVISION    "201012280000Z"
                DESCRIPTION "V1.27, modified the enum value of hwPwVCCVCapabilities and hwPwVCCVStatus."

                REVISION    "201011200000Z"
                DESCRIPTION "V1.26, modified the description."
                                             
                REVISION    "201011170000Z"
                DESCRIPTION "V1.25, updated history.
                             Added table hwPwCmdTdmDefectStatsTable.
                             Modified value range of leaf node hwPwCmdVccvFrequency."
                                
                REVISION    "201011110000Z"
                DESCRIPTION "V1.24, updated the parameters of car for hwPwCmdPwCarTable.
                             Added leaf node hwPwAtmCfgTimeout."
                
                REVISION    "201011090000Z"
                DESCRIPTION "V1.23, modified the description."
                
                REVISION    "201010110000Z"
                DESCRIPTION "V1.22, modified the description."
                
                REVISION    "201007242000Z"
                DESCRIPTION "V1.21, updated the description and format."

                REVISION    "201007192000Z"
                DESCRIPTION "V1.20, modified the position of hwMplsEcmpEnable and hwMplsL2VPNEnable."

                REVISION    "201007172000Z"
                DESCRIPTION "V1.19, modified the description of all tables."    
                             
                REVISION    "201006222000Z"
                DESCRIPTION "V1.18, added table hwpwExtTable to configure the priority, vccv and flow label of PW.
                             Added table hwMplsL2VPNTable to enable or disable the MPLS L2 VPN function.
                             Added trap hwPwCmdPwDeleted, modify traps hwPwCmdSerRecov and hwPwCmdSerFault.    
                             Modified traps hwPwCmdSerSwitchToSec and hwPwCmdSerSwitchToPri. 
                             Modified the value range of hwPwCmdRecoverWtrtime, and set the units from minute to second.
                             Modified the type of hwPwCmdPsPrimaryPwStatus, hwPwCmdPsSecondaryPwStatus BITS to INTEGER."       
                             
                REVISION    "201006112000Z"
                DESCRIPTION "V1.17, modified the value range of hwPwCmdPwTdmVclID."                
                
                REVISION    "201005292000Z"
                DESCRIPTION "V1.16, modified the value range of hwPwCmdAcBindingInboundLabel, hwPwCmdAcVlanBindingInboundLabel,
                             hwPwCmdAcPvpBindingInboundLabel, hwPwCmdAcTdmBindingInboundLabel, hwPwCmdPwInboundLabel. 
                             Modified the format of enumeration."   
                
                REVISION    "201004252000Z"
                DESCRIPTION "V1.15, modified the value range of hwPwCmdPwImaGroup."   
                             
                REVISION    "201004122000Z"
                DESCRIPTION "V1.14, modified description of leaves."   
                 
                REVISION    "201001122000Z"
                DESCRIPTION "V1.13, added leaf node hwPwCmdTunnId.
                             Added traps hwPwCmdPwStatus, hwPwCmdSerRecov, hwPwCmdSerFault,
                             hwPwCmdSerSwitchToSec, hwPwCmdSerSwitchToPri, hwPwCmdTunnSwitchToW and hwPwCmdTunnSwitchToP."
                    
                REVISION    "200911200000Z"
                DESCRIPTION "V1.12, added leaf node hwPwCmdTemplateMaxEncapcellDelay for getting the Max ATM cells encapsulate delay time.
                             Modified the node of hwPwCmdTemplateMaxAtmCells's value range to 1-31.
                             Deleted leaf nodes include hwPwCmdPwVci, hwPwCmdPwVpi, hwPwCmdPwOutboundVci and hwPwCmdPwOutboundVpi."
                           
                REVISION    "200910120000Z"
                DESCRIPTION "V1.11, added leaf node hwPwCmdPwReceiveDstUDPPort for getting UDP protocol encapsulation, UDP source port."
                
                REVISION    "200909110000Z"
                DESCRIPTION "V1.10, added leaf node hwPwCmdPwDesc to describe extra information of PW."
                
                REVISION    "200907310000Z"
                DESCRIPTION "V1.09, added table hwPwCmdSwitchoverIpAddrTable to specify information for local and remote IP address to switch over.
                             Modified the node of hwPwCmdPvcBindingConnectIndex's value range to 1-32768."
                      
                REVISION    "200605081506Z"
                DESCRIPTION "V1.00, initial revision."
            ::= { hwPw 1 }  
            
        hwPw OBJECT IDENTIFIER ::= { hwMpls 8 }   

-- Textual conventions
        SignalProtocolType ::= TEXTUAL-CONVENTION
            STATUS current
            DESCRIPTION 
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'udp' is used of udp control protocol.
                "
            SYNTAX INTEGER
                {
                ldp(1),
                static(2),
                udp(3)
                }
            
        VcStatusType ::= TEXTUAL-CONVENTION
            STATUS current
            DESCRIPTION 
                "The status of the PW and the interfaces affecting this PW.
                "
            SYNTAX INTEGER
                {
                down(1),
                up(2),
                plugout(3)
                }
            
        hwPwCmdVcNotifications OBJECT IDENTIFIER ::= { hwPwCmdMIB 1 }
        
        hwPwCmdVcSwitchWtoP NOTIFICATION-TYPE
            OBJECTS { hwPwCmdVcIndex,     -- index of working pw
                      hwPwCmdVcIndex      -- index of protect pw
                    }
            STATUS current
            DESCRIPTION 
                "This notification is generated when switch from working
                 pw to protect pw happens.
                "
            ::= { hwPwCmdVcNotifications 1 }
        
        hwPwCmdVcSwitchPtoW NOTIFICATION-TYPE
            OBJECTS { hwPwCmdVcIndex,     -- index of protect pw
                      hwPwCmdVcIndex      -- index of working pw
                    }
            STATUS current
            DESCRIPTION 
                "This notification is generated when switch from protect
                 pw to working pw happens.
                "
            ::= { hwPwCmdVcNotifications 2 }    
            
        hwPwCmdVcUp NOTIFICATION-TYPE
            OBJECTS { hwPwCmdPwID,               -- index of pw
                      hwPwCmdPwVcStatus          -- vc status of pw
                    }
            STATUS current
            DESCRIPTION 
                "This notification is generated when the vc status 
                 change from other status to up.
                "
            ::= { hwPwCmdVcNotifications 3 }
        
        hwPwCmdVcDown NOTIFICATION-TYPE
            OBJECTS { hwPwCmdPwID,               -- index of pw
                      hwPwCmdPwVcStatus          -- vc status of pw
                    }
            STATUS current
            DESCRIPTION 
                "This notification is generated when the vc status 
                 change from other status to down.
                "
            ::= { hwPwCmdVcNotifications 4 }


        --  Tables, Scalars             
        hwPwCmdObjects OBJECT IDENTIFIER ::= { hwPwCmdMIB 2 }
            
        --  PW Virtual Connection (VC) Table     
        hwPwCmdVcIndexNext OBJECT-TYPE
            SYNTAX Unsigned32
            MAX-ACCESS read-only
            STATUS current
            DESCRIPTION
                "This object contains an appropriate value to be used 
                 for hwPwCmdVcIndex when creating entries in the 
                 hwPwCmdVcTable. The value 0 indicates that no 
                 unassigned entries are available.  To obtain the 
                 value of hwPwCmdVcIndex for a new entry in the 
                 hwPwCmdVcTable, the manager issues a management 
                 protocol retrieval operation to obtain the current 
                 value of hwPwCmdVcIndex.  After each retrieval 
                 operation, the agent should modify the value to 
                 reflect the next unassigned index.  After a manager 
                 retrieves a value the agent will determine through 
                 its local policy when this index value will be made 
                 available for reuse.
                "
            ::= { hwPwCmdObjects 1 }
        
        hwPwCmdVcTable OBJECT-TYPE
            SYNTAX SEQUENCE OF HwPwCmdVcEntry
            MAX-ACCESS not-accessible
            STATUS current
            DESCRIPTION
                "This table specifies information for configuring and 
                 status monitoring that are common to all service types.
                 The index of this table is hwPwCmdVcIndex.
                "
            ::= { hwPwCmdObjects 2 }
        
        hwPwCmdVcEntry OBJECT-TYPE
            SYNTAX HwPwCmdVcEntry
            MAX-ACCESS not-accessible
            STATUS current
            DESCRIPTION
                "This table specifies information for configuring and 
                 status monitoring that are common to all service types.
                 The index of this entry is hwPwCmdVcIndex.
                "
            INDEX { hwPwCmdVcIndex }
            ::= { hwPwCmdVcTable 1 }
        
        HwPwCmdVcEntry ::=
            SEQUENCE { 
                hwPwCmdVcIndex
                    Unsigned32,
                hwPwCmdVcSignalProtocol
                    SignalProtocolType,
                hwPwCmdVcID
                    Unsigned32,
                hwPwCmdVcType
                    PwVcType,
                hwPwCmdVcPeerAddrType
                    InetAddressType,
                hwPwCmdVcPeerAddr
                    IpAddress,
                hwPwCmdVcStatus
                    VcStatusType,
                hwPwCmdVcInboundLabel
                    Unsigned32,
                hwPwCmdVcOutboundLabel
                    Unsigned32,  
                hwPwCmdVcSwitchSignalProtocol
                    SignalProtocolType, 
                hwPwCmdVcSwitchID
                    Unsigned32,
                hwPwCmdVcSwitchPeerAddrType
                    InetAddressType,
                hwPwCmdVcSwitchPeerAddr
                    IpAddress,
                hwPwCmdVcSwitchInboundLabel
                    Unsigned32,
                hwPwCmdVcSwitchOutboundLabel
                    Unsigned32,
                hwPwCmdVcGroupID
                    Unsigned32,
                hwPwCmdVcIfIndex
                    InterfaceIndex,
                hwPwCmdVcAcStatus
                    INTEGER,
                hwPwCmdVcMtu
                    Unsigned32,
                hwPwCmdVcCw
                    TruthValue,
                hwPwCmdVcVCCV
                    BITS,                    
                hwPwCmdVcBandwidth
                    Unsigned32,
                hwPwCmdVcMaxAtmCells
                    Unsigned32,
                hwPwCmdVcTnlPolicyName
                    OCTET STRING,
                hwPwCmdVcQoSBehaviorIndex
                    Unsigned32,
                hwPwCmdVcExplicitPathName
                    OCTET STRING,
                hwPwCmdVcTemplateIndex
                    Unsigned32,
                hwPwCmdVcSecondary
                    TruthValue,
                hwPwCmdVcUpTime
                    TimeStamp,
                hwPwCmdVcRowStatus
                    RowStatus
             }

        hwPwCmdVcIndex OBJECT-TYPE
            SYNTAX Unsigned32
            MAX-ACCESS not-accessible
            STATUS current
            DESCRIPTION
                "Index for the conceptual row identifying a PW within  
                 this PW Emulation table.
                "
            ::= { hwPwCmdVcEntry 1 }
        
        hwPwCmdVcSignalProtocol OBJECT-TYPE
            SYNTAX SignalProtocolType
            MAX-ACCESS read-create
            STATUS current
            DESCRIPTION
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'rsvp' indicate the use of rsvp  
                 control protocol.
                "
            ::= { hwPwCmdVcEntry 2 }
        
        hwPwCmdVcID OBJECT-TYPE
            SYNTAX Unsigned32
            MAX-ACCESS read-create
            STATUS current
            DESCRIPTION
                "Used in the outgoing PW ID field within the 'Virtual 
                 Circuit FEC Element'.
                "
            ::= { hwPwCmdVcEntry 3 }
        
        hwPwCmdVcType OBJECT-TYPE
            SYNTAX PwVcType
            MAX-ACCESS read-create
            STATUS current
            DESCRIPTION
                "This value indicate the service to be carried over 
                 this PW.
                "
            ::= { hwPwCmdVcEntry 4 }
        
        hwPwCmdVcPeerAddrType OBJECT-TYPE
            SYNTAX InetAddressType
            MAX-ACCESS read-create
            STATUS current
            DESCRIPTION
                "Denotes the address type of the peer node. It should be  
                 set to 'unknown' if PE/PW maintenance protocol is not used 
                 and the address is unknown.
                "
            DEFVAL { ipv4 }
            ::= { hwPwCmdVcEntry 5 }
        
        hwPwCmdVcPeerAddr OBJECT-TYPE
            SYNTAX IpAddress
            MAX-ACCESS read-create
            STATUS current
            DESCRIPTION
                "This object contains the value of the peer node address 
                 of the PW/PE maintenance protocol entity. This object  
                 SHOULD contain a value of all zeros if not applicable  
                 (hwPwCmdVcPeerAddrType is 'unknown').
                "
            ::= { hwPwCmdVcEntry 6 }
        
        hwPwCmdVcStatus OBJECT-TYPE
            SYNTAX VcStatusType
            MAX-ACCESS read-only
            STATUS current
            DESCRIPTION
                "Indicates the status of the PW in the local node.
                "
            ::= { hwPwCmdVcEntry 7 }
        
        hwPwCmdVcInboundLabel OBJECT-TYPE
            SYNTAX Unsigned32 (16..1023)
            MAX-ACCESS read-create
            STATUS current
            DESCRIPTION
                "The PW label used in the inbound direction (i.e. packets  
                 received from the PSN. 
                 Range: 16-1023
                 It may be set up manually if owner is 'manual' or automatically 
                 otherwise.  
                 Examples: For MPLS PSN, it represents the 20 bits of PW 
                 tag, for L2TP it represent the 32 bits Session ID. 
                 If the label is not yet known (signaling in process), the  
                 object should return a value of 0xFFFF.
                "
            ::= { hwPwCmdVcEntry 8 }
        
        hwPwCmdVcOutboundLabel OBJECT-TYPE
            SYNTAX Unsigned32 (16..1023)
            MAX-ACCESS read-create
            STATUS current
            DESCRIPTION
                "The PW label used in the outbound direction (i.e. toward  
                 the PSN). 
                 Range: 16-1023
                 It may be set up manually if owner is 'manual'  
                 or automatically otherwise. Examples: For MPLS PSN, it  
                 represents the 20 bits of PW tag, for L2TP it represent  
                 the 32 bits Session ID. 
                 If the label is not yet known (signaling in process), the  
                 object should return a value of 0xFFFF.
                "
            ::= { hwPwCmdVcEntry 9 }       
        
        hwPwCmdVcSwitchSignalProtocol OBJECT-TYPE
            SYNTAX SignalProtocolType
            MAX-ACCESS read-create
            STATUS current
            DESCRIPTION
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'rsvp' indicate the use of rsvp  
                 control protocol.
                "
            ::= { hwPwCmdVcEntry 10 }
            
        hwPwCmdVcSwitchID OBJECT-TYPE
            SYNTAX Unsigned32
            MAX-ACCESS read-create
            STATUS current
            DESCRIPTION
                "Used in the outgoing PW ID field within the 'Virtual 
                 Circuit FEC Element' of the switch pw.
                "
            ::= { hwPwCmdVcEntry 11 }

        hwPwCmdVcSwitchPeerAddrType OBJECT-TYPE
            SYNTAX InetAddressType
            MAX-ACCESS read-create
            STATUS current
            DESCRIPTION
                "Denotes the address type of the peer node of the switch pw.
                 It should be  
                 set to 'unknown' if PE/PW maintenance protocol is not used 
                 and the address is unknown.
                "
            ::= { hwPwCmdVcEntry 12 }
                                            
        hwPwCmdVcSwitchPeerAddr OBJECT-TYPE
            SYNTAX IpAddress
            MAX-ACCESS read-create
            STATUS current
            DESCRIPTION
                "This object contains the value of the peer node address of the
                 switch pw of the PW/PE maintenance protocol entity. This object  
                 SHOULD contain a value of all zeros if not applicable  
                 (hwPwCmdVcSwitchPeerAddrType is 'unknown').
                "
            ::= { hwPwCmdVcEntry 13 }
                                     
        hwPwCmdVcSwitchInboundLabel OBJECT-TYPE
            SYNTAX Unsigned32 (16..1023)
            MAX-ACCESS read-create
            STATUS current
            DESCRIPTION
                "The PW label used in the inbound direction (i.e. packets  
                 received from the PSN. 
                 Range: 16-1023
                 It may be set up manually if owner 
                 is 'manual' or automatically otherwise.  
                 Examples: For MPLS PSN, it represents the 20 bits of PW 
                 tag, for L2TP it represent the 32 bits Session ID. 
                 If the label is not yet known (signaling in process), the  
                 object should return a value of 0xFFFF.
                "
            ::= { hwPwCmdVcEntry 14 }  
                                     
        hwPwCmdVcSwitchOutboundLabel OBJECT-TYPE
            SYNTAX Unsigned32 (16..1023)
            MAX-ACCESS read-create
            STATUS current
            DESCRIPTION
                "The PW label used in the outbound direction (i.e. toward  
                 the PSN).
                 Range: 16-1023 
                 It may be set up manually if owner is 'manual'  
                 or automatically otherwise. Examples: For MPLS PSN, it  
                 represents the 20 bits of PW tag, for L2TP it represent  
                 the 32 bits Session ID. 
                 If the label is not yet known (signaling in process), the  
                 object should return a value of 0xFFFF.
                "
            ::= { hwPwCmdVcEntry 15 }  
                                               
        hwPwCmdVcGroupID OBJECT-TYPE
            SYNTAX Unsigned32
            MAX-ACCESS read-only
            STATUS current
            DESCRIPTION
                "Used in the Group ID field sent to the peer PWES  
                 within the maintenance protocol used for PW setup. 
                 Applicable if pwVcOwner equal 'pwIdFecSignaling' or  
                 'l2tpControlProtocol', should be set to zero otherwise.
                "
            ::= { hwPwCmdVcEntry 16 }

        hwPwCmdVcIfIndex OBJECT-TYPE
            SYNTAX InterfaceIndex
            MAX-ACCESS read-create
            STATUS current
            DESCRIPTION
                "Index of the interface (or the virtual interface) 
                 associated with the PW.
                "
            ::= { hwPwCmdVcEntry 17 }
        
        hwPwCmdVcAcStatus OBJECT-TYPE
            SYNTAX INTEGER
                {
                down(1),
                up(2),
                plugout(3)
                }
            MAX-ACCESS read-only
            STATUS current
            DESCRIPTION
                "Local AC status.
                 Options: 
                 1. down(1)    -indicates AC status down 
                 2. up(2)      -indicates AC status up
                 3. plugout(3) -indicates AC status plugout
                "
            ::= { hwPwCmdVcEntry 18 }
        
        hwPwCmdVcMtu OBJECT-TYPE
            SYNTAX Unsigned32
            MAX-ACCESS read-create
            STATUS current
            DESCRIPTION
                "If not equal zero, the optional Mtu object in the  
                 signaling protocol will be sent with this value,  
                 representing the locally supported MTU size over the  
                 interface (or the virtual interface) associated with the  
                 PW.
                "
            ::= { hwPwCmdVcEntry 19 }
        
        hwPwCmdVcCw OBJECT-TYPE
            SYNTAX TruthValue
            MAX-ACCESS read-create
            STATUS current
            DESCRIPTION
                "If signaling is used for PW establishment, this object  
                 indicates the status of the control word negotiation,  
                 and in both signaling or manual configuration indicates  
                 if CW is to be present or not for this PW.
                "
            ::= { hwPwCmdVcEntry 20 }

        hwPwCmdVcVCCV OBJECT-TYPE
            SYNTAX BITS
                {
                ccCw(0),
                ccAlert(1),
                ccLabel(2),
                cvIcmpping(3),
                cvLspping(4),
                cvBfd(5)
                }            
            MAX-ACCESS read-create
            STATUS current
            DESCRIPTION
                "Indicates the optional VCCV capabilities of the pw.
                 Options: 
                 1. ccCw(0)  
                 2. ccAlert(1)
                 3. ccLabel(2)
                 4. cvIcmpping(3)
                 5. cvLspping(4)
                 6. cvBfd(5)
                "
            ::= { hwPwCmdVcEntry 21 }
                    
        hwPwCmdVcBandwidth OBJECT-TYPE
            SYNTAX Unsigned32
            MAX-ACCESS read-create
            STATUS current
            DESCRIPTION
                "Indicates the bandwidth when signaling protocol is rsvp.
                "
            ::= { hwPwCmdVcEntry 22 }
        
        hwPwCmdVcMaxAtmCells OBJECT-TYPE
            SYNTAX Unsigned32
            MAX-ACCESS read-only
            STATUS current
            DESCRIPTION
                "Indicates the max cell supported when vctype is atm.
                "
            ::= { hwPwCmdVcEntry 23 }
        
        hwPwCmdVcTnlPolicyName OBJECT-TYPE
            SYNTAX OCTET STRING (SIZE (0..20))
            MAX-ACCESS read-create
            STATUS current
            DESCRIPTION
                "Indicates the tunnel policy name used.
                "
            ::= { hwPwCmdVcEntry 24 }
        
        hwPwCmdVcQoSBehaviorIndex OBJECT-TYPE
            SYNTAX Unsigned32
            MAX-ACCESS read-create
            STATUS current
            DESCRIPTION
                "Indicates the traffic behavior Index when QOS is implemented.
                "
            ::= { hwPwCmdVcEntry 25 }
        
        hwPwCmdVcExplicitPathName OBJECT-TYPE
            SYNTAX OCTET STRING (SIZE (0..20))
            MAX-ACCESS read-create
            STATUS current
            DESCRIPTION
                "Indicates the explicit path name set by the operator.
                "
            ::= { hwPwCmdVcEntry 26 }
        
        hwPwCmdVcTemplateIndex OBJECT-TYPE
            SYNTAX Unsigned32
            MAX-ACCESS read-create
            STATUS current
            DESCRIPTION
                "Indicates the pw template index referenced.
                "
            ::= { hwPwCmdVcEntry 27 }
        
        hwPwCmdVcSecondary OBJECT-TYPE
            SYNTAX TruthValue
            MAX-ACCESS read-create
            STATUS current
            DESCRIPTION
                "Indicates whether or not the secondary pw is used.
                "
            ::= { hwPwCmdVcEntry 28 }
        
        hwPwCmdVcUpTime OBJECT-TYPE
            SYNTAX TimeStamp
            MAX-ACCESS read-only
            STATUS current
            DESCRIPTION
                "Specifies the total time this PW status has been  
                 Up(1).
                "
            ::= { hwPwCmdVcEntry 29 }
        
        hwPwCmdVcRowStatus OBJECT-TYPE
            SYNTAX RowStatus
            MAX-ACCESS read-create
            STATUS current
            DESCRIPTION
                "For creating and modifying this row. None of the 
                 read-create objects in the conceptual rows may be changed  
                 when this object is in the active(1) state.
                "
            ::= { hwPwCmdVcEntry 30 }

        hwPwCmdVcTnlTable OBJECT-TYPE
            SYNTAX SEQUENCE OF HwPwCmdVcTnlEntry
            MAX-ACCESS not-accessible
            STATUS current
            DESCRIPTION
                "This table provides per-PW related tunnel information.
                 The indexes of this table are hwPwCmdVcIndex and hwPwCmdVcTnlIndex,
                 hwPwCmdVcIndexis set in hwPwCmdVcTable table.
                "
            ::= { hwPwCmdObjects 3 }

        hwPwCmdVcTnlEntry OBJECT-TYPE
            SYNTAX HwPwCmdVcTnlEntry
            MAX-ACCESS not-accessible
            STATUS current
            DESCRIPTION
                "This table provides per-PW related tunnel information.
                 The indexes of this entry are hwPwCmdVcIndex and hwPwCmdVcTnlIndex,
                 hwPwCmdVcIndexis set in hwPwCmdVcTable table.
                "
            INDEX { hwPwCmdVcIndex,
                    hwPwCmdVcTnlIndex
                  }
            ::= { hwPwCmdVcTnlTable 1 }

        HwPwCmdVcTnlEntry ::=
            SEQUENCE { 
                hwPwCmdVcTnlIndex
                    Unsigned32
            }

        hwPwCmdVcTnlIndex OBJECT-TYPE
            SYNTAX Unsigned32
            MAX-ACCESS read-only
            STATUS current
            DESCRIPTION
                "Indicates the tunnel index related to each PW.
                "
            ::= { hwPwCmdVcTnlEntry 1 }
                     
        hwPwCmdRemoteVcTable OBJECT-TYPE
            SYNTAX SEQUENCE OF HwPwCmdRemoteVcEntry
            MAX-ACCESS not-accessible
            STATUS current
            DESCRIPTION
                "This table provides remote PW information for  
                 each local PW.The index of this table is hwPwCmdRemoteVcID.
                "
            ::= { hwPwCmdObjects 4 }
        
        hwPwCmdRemoteVcEntry OBJECT-TYPE
            SYNTAX HwPwCmdRemoteVcEntry
            MAX-ACCESS not-accessible
            STATUS current
            DESCRIPTION
                "This table provides remote PW information for  
                 each local PW.The index of this entry is hwPwCmdRemoteVcID.
                "
            AUGMENTS { hwPwCmdVcEntry }
            ::= { hwPwCmdRemoteVcTable 1 }
        
        HwPwCmdRemoteVcEntry ::=
            SEQUENCE { 
                hwPwCmdRemoteVcID
                    Unsigned32,
                hwPwCmdRemoteVcType
                    PwVcType,
                hwPwCmdRemoteVcStatus
                    VcStatusType,
                hwPwCmdRemoteVcGroupID
                    Unsigned32,
                hwPwCmdRemoteVcMtu
                    Unsigned32,
                hwPwCmdRemoteVcCw
                    TruthValue,
                hwPwCmdRemoteVcMaxAtmCells
                    Unsigned32,
                hwPwCmdRemoteVcNotif
                    TruthValue,
                hwPwCmdRemoteVcSwitchID
                    Unsigned32,
                hwPwCmdRemoteVcSwitchType
                    PwVcType,
                hwPwCmdRemoteVcSwitchStatus
                    VcStatusType,
                hwPwCmdRemoteVcSwitchGroupID
                    Unsigned32,
                hwPwCmdRemoteVcSwitchMtu
                    Unsigned32,
                hwPwCmdRemoteVcSwitchCw
                    TruthValue,
                hwPwCmdRemoteVcSwitchMaxAtmCells
                    Unsigned32,
                hwPwCmdRemoteVcSwitchNotif
                    TruthValue                    
             }

        hwPwCmdRemoteVcID OBJECT-TYPE
            SYNTAX Unsigned32
            MAX-ACCESS read-only
            STATUS current
            DESCRIPTION
                "Used in the outgoing PW ID field within the 'Virtual 
                 Circuit FEC Element' of the remote PW.
                "
            ::= { hwPwCmdRemoteVcEntry 1 }
        
        hwPwCmdRemoteVcType OBJECT-TYPE
            SYNTAX PwVcType
            MAX-ACCESS read-only
            STATUS current
            DESCRIPTION
                "This value indicate the service to be carried over 
                 the remote PW.
                "
            ::= { hwPwCmdRemoteVcEntry 2 }
        
        hwPwCmdRemoteVcStatus OBJECT-TYPE
            SYNTAX VcStatusType
            MAX-ACCESS read-only
            STATUS current
            DESCRIPTION
                "Indicates the status of the remote PW.
                "
            ::= { hwPwCmdRemoteVcEntry 3 }
        
        hwPwCmdRemoteVcGroupID OBJECT-TYPE
            SYNTAX Unsigned32
            MAX-ACCESS read-only
            STATUS current
            DESCRIPTION
                "Indicates the Group ID field of the remote PW.
                "
            ::= { hwPwCmdRemoteVcEntry 4 }
        
        hwPwCmdRemoteVcMtu OBJECT-TYPE
            SYNTAX Unsigned32
            MAX-ACCESS read-only
            STATUS current
            DESCRIPTION
                "Indicates the supported MTU size of the remote PW.
                "
            ::= { hwPwCmdRemoteVcEntry 5 }
        
        hwPwCmdRemoteVcCw OBJECT-TYPE
            SYNTAX TruthValue
            MAX-ACCESS read-only
            STATUS current
            DESCRIPTION
                "Indicates the control word capability of the remote PW.
                "
            ::= { hwPwCmdRemoteVcEntry 6 }
        
        hwPwCmdRemoteVcMaxAtmCells OBJECT-TYPE
            SYNTAX Unsigned32
            MAX-ACCESS read-only
            STATUS current
            DESCRIPTION
                "Indicates the max cell supported of the remote PW 
                 when vctype is atm.
                "
            ::= { hwPwCmdRemoteVcEntry 7 }
        
        hwPwCmdRemoteVcNotif OBJECT-TYPE
            SYNTAX TruthValue
            MAX-ACCESS read-only
            STATUS current
            DESCRIPTION
                "Indicates notification is supported by the remote PW.
                "
            ::= { hwPwCmdRemoteVcEntry 8 }

        hwPwCmdRemoteVcSwitchID OBJECT-TYPE
            SYNTAX Unsigned32
            MAX-ACCESS read-only
            STATUS current
            DESCRIPTION
                "Used in the outgoing PW ID field within the 'Virtual 
                 Circuit FEC Element' of the switch PW.
                "
            ::= { hwPwCmdRemoteVcEntry 9 }
        
        hwPwCmdRemoteVcSwitchType OBJECT-TYPE
            SYNTAX PwVcType
            MAX-ACCESS read-only
            STATUS current
            DESCRIPTION
                "This value indicate the service to be carried over 
                 the switch PW.
                "
            ::= { hwPwCmdRemoteVcEntry 10 }
        
        hwPwCmdRemoteVcSwitchStatus OBJECT-TYPE
            SYNTAX VcStatusType
            MAX-ACCESS read-only
            STATUS current
            DESCRIPTION
                "Indicates the status of the switch PW.
                "
            ::= { hwPwCmdRemoteVcEntry 11 }
        
        hwPwCmdRemoteVcSwitchGroupID OBJECT-TYPE
            SYNTAX Unsigned32
            MAX-ACCESS read-only
            STATUS current
            DESCRIPTION
                "Indicates the Group ID field of the switch PW.
                "
            ::= { hwPwCmdRemoteVcEntry 12 }
        
        hwPwCmdRemoteVcSwitchMtu OBJECT-TYPE
            SYNTAX Unsigned32
            MAX-ACCESS read-only
            STATUS current
            DESCRIPTION
                "Indicates the supported MTU size of the switch PW.
                "
            ::= { hwPwCmdRemoteVcEntry 13 }
        
        hwPwCmdRemoteVcSwitchCw OBJECT-TYPE
            SYNTAX TruthValue
            MAX-ACCESS read-only
            STATUS current
            DESCRIPTION
                "Indicates the control word capability of the switch PW.
                "
            ::= { hwPwCmdRemoteVcEntry 14 }
        
        hwPwCmdRemoteVcSwitchMaxAtmCells OBJECT-TYPE
            SYNTAX Unsigned32
            MAX-ACCESS read-only
            STATUS current
            DESCRIPTION
                "Indicates the max cell supported of the switch PW 
                 when vctype is atm.
                "
            ::= { hwPwCmdRemoteVcEntry 15 }
        
        hwPwCmdRemoteVcSwitchNotif OBJECT-TYPE
            SYNTAX TruthValue
            MAX-ACCESS read-only
            STATUS current
            DESCRIPTION
                "Indicates notification is supported by the switch PW.
                "
            ::= { hwPwCmdRemoteVcEntry 16 }
        
        hwPwCmdAcBindingTable OBJECT-TYPE
            SYNTAX SEQUENCE OF HwPwCmdAcBindingEntry
            MAX-ACCESS not-accessible
            STATUS current
            DESCRIPTION
                "This table specifies information for configuring and 
                 status monitoring for PW used in fixed network.
                 The indexes of this table are hwPwCmdAcBindingConnectIndex and hwPwCmdAcBindingPrimOrSecondary.
                "
            ::= { hwPwCmdObjects 5 }
        
        hwPwCmdAcBindingEntry OBJECT-TYPE
            SYNTAX HwPwCmdAcBindingEntry
            MAX-ACCESS not-accessible
            STATUS current
            DESCRIPTION
                "This table specifies information for configuring and 
                 status monitoring for PW used in fixed network.
                 The indexes of this entry are hwPwCmdAcBindingConnectIndex and hwPwCmdAcBindingPrimOrSecondary.
                "
            INDEX { hwPwCmdAcBindingConnectIndex, hwPwCmdAcBindingPrimOrSecondary }
            ::= { hwPwCmdAcBindingTable 1 }
        
        HwPwCmdAcBindingEntry ::=
            SEQUENCE { 
                hwPwCmdAcBindingConnectIndex
                    Unsigned32,
                hwPwCmdAcBindingVcID
                    Unsigned32,  
                hwPwCmdAcBindingVcStatus
                    VcStatusType,
                hwPwCmdAcBindingTemplateName
                    OCTET STRING,
                hwPwCmdAcBindingOutboundVpi
                    Integer32,
                hwPwCmdAcBindingOutboundVci
                    Integer32,          
                hwPwCmdAcBindingSignalProtocol
                    SignalProtocolType,
                hwPwCmdAcBindingOutboundLabel
                    Integer32,
                hwPwCmdAcBindingInboundLabel
                    Integer32,
                hwPwCmdAcBindingRowStatus
                    RowStatus,                          
                hwPwCmdAcBindingPrimOrSecondary 
                    INTEGER
             }

        hwPwCmdAcBindingConnectIndex OBJECT-TYPE
            SYNTAX Unsigned32 (1..32768)
            MAX-ACCESS not-accessible
            STATUS current
            DESCRIPTION
                "Indicates the connect index referenced.
                 Range: 1-32768
                "
            ::= { hwPwCmdAcBindingEntry 1 }

        hwPwCmdAcBindingVcID OBJECT-TYPE
            SYNTAX Unsigned32 (1..4294967295)
            MAX-ACCESS read-create
            STATUS current
            DESCRIPTION
                "Used in the outgoing PW ID field within the 'Virtual 
                 Circuit FEC Element'.
                 Range: 1-4294967295
                "
            ::= { hwPwCmdAcBindingEntry 2 }
        
        hwPwCmdAcBindingVcStatus OBJECT-TYPE
            SYNTAX VcStatusType
            MAX-ACCESS read-only
            STATUS current
            DESCRIPTION
                "Indicates the status of the PW: 
                 down(1),
                 up(2),
                 plugout(3).
                "
            ::= { hwPwCmdAcBindingEntry 3 }
        
        hwPwCmdAcBindingTemplateName OBJECT-TYPE
            SYNTAX OCTET STRING (SIZE (1..19))
            MAX-ACCESS read-create
            STATUS current
            DESCRIPTION
                "Indicates the description string of the template,
                 MUST be NULL string if not applicable or not known yet.
                "
            ::= { hwPwCmdAcBindingEntry 4 }
                
        hwPwCmdAcBindingOutboundVpi OBJECT-TYPE
            SYNTAX Integer32 (0..4095)
            MAX-ACCESS read-create
            STATUS current
            DESCRIPTION
                "VPI value of this ATM VC. 
                 Range: 0-4095
                 If the pwVcType is atmNto1Transparent then the value 
                 will be set to zero.
                "
            ::= { hwPwCmdAcBindingEntry 5 }
        
        hwPwCmdAcBindingOutboundVci OBJECT-TYPE
            SYNTAX Integer32 (32..65535)
            MAX-ACCESS read-create
            STATUS current
            DESCRIPTION
                "VCI value of this ATM VC.
                 Range: 32-65535 
                 If the pwVcType is atmNto1Transparent, atmCell1to1Vpc or
                 atmCellNto1Vpc then the value should be set to zero.
                "
            ::= { hwPwCmdAcBindingEntry 6 }

        hwPwCmdAcBindingSignalProtocol OBJECT-TYPE
            SYNTAX SignalProtocolType
            MAX-ACCESS read-create
            STATUS current
            DESCRIPTION
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'rsvp' indicate the use of rsvp  
                 control protocol.
                "
            ::= { hwPwCmdAcBindingEntry 7 }
                    
        hwPwCmdAcBindingOutboundLabel OBJECT-TYPE
            SYNTAX Integer32 (16..1048575)
            MAX-ACCESS read-create
            STATUS current
            DESCRIPTION
                "The PW label used in the outbound direction (i.e. toward  
                 the PSN). 
                 Range: 16-1048575
                 It may be set up manually if owner is 'manual'  
                 or automatically otherwise. Examples: For MPLS PSN, it  
                 represents the 20 bits of PW tag, for L2TP it represent  
                 the 32 bits Session ID. 
                 If the label is not yet known (signaling in process), the  
                 object should return a value of 0xFFFF.
                "
            ::= { hwPwCmdAcBindingEntry 8 }
        
        hwPwCmdAcBindingInboundLabel OBJECT-TYPE
            SYNTAX Integer32 (16..1048575)
            MAX-ACCESS read-create
            STATUS current
            DESCRIPTION
                "The PW label used in the inbound direction (i.e. packets  
                 received from the PSN. 
                 Range: 16-1048575
                 It may be set up manually if owner 
                 is 'manual' or automatically otherwise.  
                 Examples: For MPLS PSN, it represents the 20 bits of PW 
                 tag, for L2TP it represent the 32 bits Session ID. 
                 If the label is not yet known (signaling in process), the  
                 object should return a value of 0xFFFF.
                "
            ::= { hwPwCmdAcBindingEntry 9 }

        hwPwCmdAcBindingRowStatus OBJECT-TYPE
            SYNTAX RowStatus (1..6)
            MAX-ACCESS read-create
            STATUS current
            DESCRIPTION
                "For creating and modifying this row. None of the 
                 read-create objects in the conceptual rows may be changed  
                 when this object is in the active(1) state.
                "
            ::= { hwPwCmdAcBindingEntry 10 }
            
        hwPwCmdAcBindingPrimOrSecondary OBJECT-TYPE
            SYNTAX INTEGER
                {
                primaryPW(1),
                secondaryPW(2)
                }  
            
            MAX-ACCESS not-accessible
            STATUS current
            DESCRIPTION
                "This value indicate Primary PW or Secondary PW.
                 Options: 
                 1. primaryPW(1)   -indicates primary PW
                 2. secondaryPW(2) -indicates secondary PW
                "
            ::= { hwPwCmdAcBindingEntry 11 }
         
        hwPwCmdTemplateIndexNext OBJECT-TYPE
            SYNTAX Unsigned32
            MAX-ACCESS read-only
            STATUS current
            DESCRIPTION
                "This object contains an appropriate value to be used 
                 for hwPwCmdTemplateIndex when creating entries in the 
                 hwPwCmdTemplateTable. The value 0 indicates that no 
                 unassigned entries are available.  To obtain the 
                 value of hwPwCmdTemplateIndex for a new entry in the 
                 hwPwCmdTemplateTable, the manager issues a management 
                 protocol retrieval operation to obtain the current 
                 value of hwPwCmdVcIndex.  After each retrieval 
                 operation, the agent should modify the value to 
                 reflect the next unassigned index.  After a manager 
                 retrieves a value the agent will determine through 
                 its local policy when this index value will be made 
                 available for reuse.
                "
            ::= { hwPwCmdObjects 6 }
        
        hwPwCmdTemplateTable OBJECT-TYPE
            SYNTAX SEQUENCE OF HwPwCmdTemplateEntry
            MAX-ACCESS not-accessible
            STATUS current
            DESCRIPTION
                "This table specifies information for configuring and 
                 status monitoring to pw template.
                 The index of this table is hwPwCmdTemplateIndex.
                "
            ::= { hwPwCmdObjects 7 }
        
        hwPwCmdTemplateEntry OBJECT-TYPE
            SYNTAX HwPwCmdTemplateEntry
            MAX-ACCESS not-accessible
            STATUS current
            DESCRIPTION
                "This table specifies information for configuring and 
                 status monitoring to pw template.
                 The index of this entry is hwPwCmdTemplateIndex.
                "
            INDEX { hwPwCmdTemplateIndex }
            ::= { hwPwCmdTemplateTable 1 }
        
        HwPwCmdTemplateEntry ::=
            SEQUENCE { 
                hwPwCmdTemplateIndex
                    Unsigned32,
                hwPwCmdTemplateName
                    OCTET STRING,
                hwPwCmdTemplateVcType
                    PwVcType,
                hwPwCmdTemplatePeerAddrType
                    InetAddressType,
                hwPwCmdTemplatePeerAddr
                    IpAddress,
                hwPwCmdTemplateMtu
                    Unsigned32,
                hwPwCmdTemplateCw
                    TruthValue,
                hwPwCmdTemplateVCCV
                    BITS,
                hwPwCmdTemplateFrag
                    TruthValue,
                hwPwCmdTemplateBandwidth
                    Unsigned32,        
                hwPwCmdTemplateMaxAtmCells
                    Unsigned32,
                hwPwCmdTemplateTnlPolicyName
                    OCTET STRING,
                hwPwCmdTemplateQoSBehaviorIndex
                    Integer32,
                hwPwCmdTemplateExplicitPathName
                    OCTET STRING,
                hwPwCmdTemplateTdmJitterBuffer
                    Unsigned32,
                hwPwCmdTemplateTdmLoadTime
                    Unsigned32,
                hwPwCmdTemplateTdmRTP
                    INTEGER,
                hwPwCmdTemplateRowStatus
                    RowStatus,
                hwPwCmdTemplateTdmTimeSlotNum
                    Unsigned32,
                hwPwCmdTemplateMaxEncapcellDelay
                    Unsigned32,
                hwPwCmdTemplateFlowLabel
                    BITS
             }

        hwPwCmdTemplateIndex OBJECT-TYPE
            SYNTAX Unsigned32
            MAX-ACCESS not-accessible
            STATUS current
            DESCRIPTION
                "Index for the conceptual row identifying a PW template within  
                 this PW template table.
                "
            ::= { hwPwCmdTemplateEntry 1 }
        
        hwPwCmdTemplateName OBJECT-TYPE
            SYNTAX OCTET STRING (SIZE (1..19))
            MAX-ACCESS read-create
            STATUS current
            DESCRIPTION
                "Indicates the description string of the template,
                 MUST be NULL string if not applicable or not known yet.
                "
            ::= { hwPwCmdTemplateEntry 2 }
        
        hwPwCmdTemplateVcType OBJECT-TYPE
            SYNTAX PwVcType
            MAX-ACCESS read-create
            STATUS current
            DESCRIPTION
                "This value indicate the service to be carried over 
                 this template.
                "
            ::= { hwPwCmdTemplateEntry 3 }
        
        hwPwCmdTemplatePeerAddrType OBJECT-TYPE
            SYNTAX InetAddressType
            MAX-ACCESS read-create
            STATUS current
            DESCRIPTION
                "Denotes the address type of the peer node. It should be  
                 set to 'unknown' if PE/PW maintenance protocol is not used 
                 and the address is unknown.
                "
            ::= { hwPwCmdTemplateEntry 4 }
        
        hwPwCmdTemplatePeerAddr OBJECT-TYPE
            SYNTAX IpAddress
            MAX-ACCESS read-create
            STATUS current
            DESCRIPTION
                "This object contains the value of the peer node address 
                 of the PW/PE maintenance protocol entity. This object  
                 SHOULD contain a value of all zeros if not applicable  
                 (hwPwCmdTemplatePeerAddrType is 'unknown').
                "
            ::= { hwPwCmdTemplateEntry 5 }
        
        hwPwCmdTemplateMtu OBJECT-TYPE
            SYNTAX Unsigned32 (328..1710)
            MAX-ACCESS read-create
            STATUS current
            DESCRIPTION
                "Indicates the supported MTU size of the switch PW.
                 Range: 328-1710
                "
            ::= { hwPwCmdTemplateEntry 6 }
        
        hwPwCmdTemplateCw OBJECT-TYPE
            SYNTAX TruthValue
            MAX-ACCESS read-create
            STATUS current
            DESCRIPTION
                "Indicates the control word capability of the switch PW.
                "
            ::= { hwPwCmdTemplateEntry 7 }
        
        hwPwCmdTemplateVCCV OBJECT-TYPE
            SYNTAX BITS
                {
                ccCw(0),
                ccAlert(1),
                ccLabel(2),
                cvIcmpping(3),
                cvLspping(4),
                cvBfd(5)
                }            
            MAX-ACCESS read-create
            STATUS current
            DESCRIPTION
                "Indicates the optional VCCV capabilities of the pw.
                 Options: 
                 1. ccCw(0)
                 2. ccAlert(1)
                 3. ccLabel(2)
                 4. cvIcmpping(3)
                 5. cvLspping(4)
                 6. cvBfd(5)
                "
            ::= { hwPwCmdTemplateEntry 8 }
        
        hwPwCmdTemplateFrag OBJECT-TYPE
            SYNTAX TruthValue
            MAX-ACCESS read-create
            STATUS current
            DESCRIPTION
                "Indicates whether or not fragmentation is supported.
                "
            ::= { hwPwCmdTemplateEntry 9 }
        
        hwPwCmdTemplateBandwidth OBJECT-TYPE
            SYNTAX Unsigned32
            MAX-ACCESS read-create
            STATUS current
            DESCRIPTION
                "Indicates the bandwidth when signaling protocol is rsvp.
                "
            ::= { hwPwCmdTemplateEntry 10 }   
        
        hwPwCmdTemplateMaxAtmCells OBJECT-TYPE
            SYNTAX Unsigned32 (1..31)
            MAX-ACCESS read-create
            STATUS current
            DESCRIPTION
                "Indicates the max ATM cells when encapsulation is ATM.
                 Range: 1-31
                 Default: 1
                "
            DEFVAL { 1 }
            ::= { hwPwCmdTemplateEntry 11 }
        
        hwPwCmdTemplateTnlPolicyName OBJECT-TYPE
            SYNTAX OCTET STRING (SIZE (0..20))
            MAX-ACCESS read-create
            STATUS current
            DESCRIPTION
                "Indicates the tunnel policy name used.
                "
            ::= { hwPwCmdTemplateEntry 12 }
        
        hwPwCmdTemplateQoSBehaviorIndex OBJECT-TYPE
            SYNTAX Integer32
            MAX-ACCESS read-create
            STATUS current
            DESCRIPTION
                "Indicates the traffic behavior Index when QOS is implemented.
                "
            ::= { hwPwCmdTemplateEntry 13 }
        
        hwPwCmdTemplateExplicitPathName OBJECT-TYPE
            SYNTAX OCTET STRING (SIZE (0..20))
            MAX-ACCESS read-create
            STATUS current
            DESCRIPTION
                "Indicates the explicit path name set by the operator.
                "
            ::= { hwPwCmdTemplateEntry 14 }
        
        hwPwCmdTemplateTdmJitterBuffer OBJECT-TYPE
            SYNTAX Unsigned32 (500..128000)
            UNITS "us"
            MAX-ACCESS read-create
            STATUS current
            DESCRIPTION
                "Indicates the jitter buffer size of TDM PW.
                 Range: 500-128000
                 Default: 2000
                 Unit: microsecond
                "
            DEFVAL { 2000 }
            ::= { hwPwCmdTemplateEntry 15 }

        hwPwCmdTemplateTdmLoadTime OBJECT-TYPE
            SYNTAX Unsigned32 (125..5000)
            UNITS "byte"
            MAX-ACCESS read-create
            STATUS current
            DESCRIPTION
                "Indicates the load time value of TDM PW.
                 Range: 125-5000
                 Default: 1000
                 Unit: byte                
                "
            DEFVAL { 1000 }
            ::= { hwPwCmdTemplateEntry 16 }  
            
        hwPwCmdTemplateTdmRTP OBJECT-TYPE
            SYNTAX INTEGER
                {
                disable(0),
                enable(1)
                }
            MAX-ACCESS read-create
            STATUS current
            DESCRIPTION
                "Indicates enable or disable RTP of TDM PW.
                 Options: 
                 1. disable(0) -indicates disable RTP
                 2. enable(1)  -indicates enable RTP
                 Default: disable(0)
                "
            DEFVAL { disable }
            ::= { hwPwCmdTemplateEntry 17 }
        
        hwPwCmdTemplateRowStatus OBJECT-TYPE
            SYNTAX RowStatus
            MAX-ACCESS read-create
            STATUS current
            DESCRIPTION
                "For creating and modifying this row. None of the 
                 read-create objects in the conceptual rows may be changed  
                 when this object is in the active(1) state.
                "
            ::= { hwPwCmdTemplateEntry 18 }
            
        hwPwCmdTemplateTdmTimeSlotNum OBJECT-TYPE
            SYNTAX Unsigned32 (1..32)
            UNITS "byte"
            MAX-ACCESS read-create
            STATUS current
            DESCRIPTION
                "Indicates the time slot Num of TDM PW.
                 Range: 1-32
                 Default: 32
                 Unit: byte 
                "
            DEFVAL { 32 }
            ::= { hwPwCmdTemplateEntry 19 }
                        
        hwPwCmdTemplateMaxEncapcellDelay OBJECT-TYPE
            SYNTAX Unsigned32 (0..50)
            UNITS "ms"
            MAX-ACCESS read-create
            STATUS current
            DESCRIPTION
                "Indicates the Max ATM cells encapsulate delay time.
                 Range: 0-50
                 Default: 0
                 Unit: millisecond
                "
            DEFVAL { 0 }
            ::= { hwPwCmdTemplateEntry 20 }
            
        hwPwCmdTemplateFlowLabel OBJECT-TYPE
            SYNTAX BITS
                {
                            sip(0),
                            dip(1),
                            smac(2),
                            dmac(3)
                }            
            MAX-ACCESS read-create
            STATUS current
            DESCRIPTION
                "Indicates the optional flow label capabilities of the pw.
                "
            ::= { hwPwCmdTemplateEntry 21 }
        
        hwPwCmdOperTable OBJECT-TYPE
            SYNTAX SEQUENCE OF HwPwCmdOperEntry
            MAX-ACCESS not-accessible
            STATUS current
            DESCRIPTION
                "This table specifies the reset operation that can be
                 done to the PW or PW template.
                 The index of this table is hwPwCmdOperIndex.
                "
            ::= { hwPwCmdObjects 8 }
        
        hwPwCmdOperEntry OBJECT-TYPE
            SYNTAX HwPwCmdOperEntry
            MAX-ACCESS not-accessible
            STATUS current
            DESCRIPTION
                "This table specifies the reset operation that can be
                 done to the PW or PW template.
                 The index of this entry is hwPwCmdOperIndex.
                "
            INDEX { hwPwCmdOperIndex }
            ::= { hwPwCmdOperTable 1 }
        
        HwPwCmdOperEntry ::=
            SEQUENCE { 
                hwPwCmdOperIndex
                    Unsigned32,
                hwPwCmdOperType
                    INTEGER,
                hwPwCmdOperVcOrPwtIndex
                    Unsigned32,
                hwPwCmdOperStatus
                    INTEGER,
                hwPwCmdOperTimeStamp
                    TimeStamp,
                hwPwCmdOperRowStatus
                    RowStatus
             }

        hwPwCmdOperIndex OBJECT-TYPE
            SYNTAX Unsigned32
            MAX-ACCESS not-accessible
            STATUS current
            DESCRIPTION
                "Index for the conceptual row.
                "
            ::= { hwPwCmdOperEntry 1 }
        
        hwPwCmdOperType OBJECT-TYPE
            SYNTAX INTEGER
                {
                vcindex(1),
                pwtindex(2)
                }
            MAX-ACCESS read-create
            STATUS current
            DESCRIPTION
                "Specifies the reset object.
                 Options:
                 1. vcindex(1)   -indicates PW index
                 2. pwtindex(2)  -indicates PW template index
                "
            ::= { hwPwCmdOperEntry 2 }
        
        hwPwCmdOperVcOrPwtIndex OBJECT-TYPE
            SYNTAX Unsigned32
            MAX-ACCESS read-create
            STATUS current
            DESCRIPTION
                "Specifies the object index to be reset.
                "
            ::= { hwPwCmdOperEntry 3 }
        
        hwPwCmdOperStatus OBJECT-TYPE
            SYNTAX INTEGER
                {
                success(1),
                pwNotExist(2),
                pwTemplateNotExist(3),
                resetFailure(4),
                unknown(5)
                }
            MAX-ACCESS read-only
            STATUS current
            DESCRIPTION
                "Indicates the result of the reset operation.
                 Options:
                 1. success(1)            -indicates operation success
                 2. pwNotExist(2)         -indicates PW not exist
                 3. pwTemplateNotExist(3) -indicates PW template not exist
                 4. resetFailure(4)       -indicates reset PW failure
                 5. unknown(5)            -indicates unknown operation status
                "
            ::= { hwPwCmdOperEntry 4 }
        
        hwPwCmdOperTimeStamp OBJECT-TYPE
            SYNTAX TimeStamp
            MAX-ACCESS read-only
            STATUS current
            DESCRIPTION
                "Specifies the total time since last reset operation has been  
                 done.
                "
            ::= { hwPwCmdOperEntry 5 }
        
        hwPwCmdOperRowStatus OBJECT-TYPE
            SYNTAX RowStatus
            MAX-ACCESS read-create
            STATUS current
            DESCRIPTION
                "For creating and deleting this row. None of the 
                 read-create objects in the conceptual rows may be changed  
                 when this object is in the active(1) state.
                "
            ::= { hwPwCmdOperEntry 6 }
        
        hwPwCmdVcSwitchNotifEnable OBJECT-TYPE
            SYNTAX TruthValue
            MAX-ACCESS read-write
            STATUS current
            DESCRIPTION
                "If this object is set to true(1), then it enables 
                 the emission of hwPwCmdVcSwitchWtoP and hwPwCmdVcSwitchPtoW 
                 notifications; otherwise these notifications are not 
                 emitted, 
                 DEFVAL { false }"
            ::= { hwPwCmdObjects 9 }


        hwPwCmdAcVlanBindingTable OBJECT-TYPE
            SYNTAX SEQUENCE OF HwPwCmdAcVlanBindingEntry
            MAX-ACCESS not-accessible
            STATUS current
            DESCRIPTION
                "This table specifies information for configuring and 
                 status monitoring for PW used in fixed network.
                 The indexes of this table are hwPwCmdAcVlanBindingVlanID and hwPwCmdAcVlanBindingPrimOrSecondary.
                "
            ::= { hwPwCmdObjects 10 }
        
        hwPwCmdAcVlanBindingEntry OBJECT-TYPE
            SYNTAX HwPwCmdAcVlanBindingEntry
            MAX-ACCESS not-accessible
            STATUS current
            DESCRIPTION
                "This table specifies information for configuring and 
                 status monitoring for PW used in fixed network.
                 The indexes of this entry are hwPwCmdAcVlanBindingVlanID and hwPwCmdAcVlanBindingPrimOrSecondary.
                "
            INDEX { hwPwCmdAcVlanBindingVlanID, hwPwCmdAcVlanBindingPrimOrSecondary }
            ::= { hwPwCmdAcVlanBindingTable 1 }
        
        HwPwCmdAcVlanBindingEntry ::=
            SEQUENCE { 
                hwPwCmdAcVlanBindingVlanID
                    Unsigned32,
                hwPwCmdAcVlanBindingVcID
                    Unsigned32,  
                hwPwCmdAcVlanBindingVcStatus
                    VcStatusType,
                hwPwCmdAcVlanBindingTemplateName
                    OCTET STRING,       
                hwPwCmdAcVlanBindingSignalProtocol
                    SignalProtocolType,
                hwPwCmdAcVlanBindingOutboundLabel
                    Integer32,
                hwPwCmdAcVlanBindingInboundLabel
                    Integer32,
                hwPwCmdAcVlanBindingRowStatus
                    RowStatus,
                hwPwCmdAcVlanBindingPrimOrSecondary 
                    INTEGER
             }

        hwPwCmdAcVlanBindingVlanID OBJECT-TYPE
            SYNTAX Unsigned32 (2..4093)
            MAX-ACCESS not-accessible
            STATUS current
            DESCRIPTION
                "Indicates the VLAN ID referenced.
                 Range: 2-4093
                "
            ::= { hwPwCmdAcVlanBindingEntry 1 }

        hwPwCmdAcVlanBindingVcID OBJECT-TYPE
            SYNTAX Unsigned32 (1..4294967295)
            MAX-ACCESS read-create
            STATUS current
            DESCRIPTION
                "Used in the outgoing PW ID field within the 'Virtual 
                 Circuit FEC Element'.
                 Range: 1-4294967295
                "
            ::= { hwPwCmdAcVlanBindingEntry 2 }
        
        hwPwCmdAcVlanBindingVcStatus OBJECT-TYPE
            SYNTAX VcStatusType
            MAX-ACCESS read-only
            STATUS current
            DESCRIPTION
                "Indicates the status of the PW: 
                 down(1),
                 up(2),
                 plugout(3).
                "
            ::= { hwPwCmdAcVlanBindingEntry 3 }
        
        hwPwCmdAcVlanBindingTemplateName OBJECT-TYPE
            SYNTAX OCTET STRING (SIZE (1..19))
            MAX-ACCESS read-create
            STATUS current
            DESCRIPTION
                "Indicates the description string of the template,
                 MUST be NULL string if not applicable or not known yet.
                "
            ::= { hwPwCmdAcVlanBindingEntry 4 }
                
        hwPwCmdAcVlanBindingSignalProtocol OBJECT-TYPE
            SYNTAX SignalProtocolType
            MAX-ACCESS read-create
            STATUS current
            DESCRIPTION
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'rsvp' indicate the use of rsvp  
                 control protocol.
                "
            ::= { hwPwCmdAcVlanBindingEntry 5 }
                    
        hwPwCmdAcVlanBindingOutboundLabel OBJECT-TYPE
            SYNTAX Integer32 (16..1048575)
            MAX-ACCESS read-create
            STATUS current
            DESCRIPTION
                "The PW label used in the outbound direction (i.e. toward  
                 the PSN). 
                 Range: 16-1048575
                 It may be set up manually if owner is 'manual'  
                 or automatically otherwise. Examples: For MPLS PSN, it  
                 represents the 20 bits of PW tag, for L2TP it represent  
                 the 32 bits Session ID. 
                 If the label is not yet known (signaling in process), the  
                 object should return a value of 0xFFFF.
                "
            ::= { hwPwCmdAcVlanBindingEntry 6 }
        
        hwPwCmdAcVlanBindingInboundLabel OBJECT-TYPE
            SYNTAX Integer32 (16..1048575)
            MAX-ACCESS read-create
            STATUS current
            DESCRIPTION
                "The PW label used in the inbound direction (i.e. packets  
                 received from the PSN.
                 Range: 16-1048575 
                 It may be set up manually if owner 
                 is 'manual' or automatically otherwise.  
                 Examples: For MPLS PSN, it represents the 20 bits of PW 
                 tag, for L2TP it represent the 32 bits Session ID. 
                 If the label is not yet known (signaling in process), the  
                 object should return a value of 0xFFFF.
                "
            ::= { hwPwCmdAcVlanBindingEntry 7 }

        hwPwCmdAcVlanBindingRowStatus OBJECT-TYPE
            SYNTAX RowStatus (1..6)
            MAX-ACCESS read-create
            STATUS current
            DESCRIPTION
                "For creating and modifying this row. None of the 
                 read-create objects in the conceptual rows may be changed  
                 when this object is in the active(1) state.
                "
            ::= { hwPwCmdAcVlanBindingEntry 8 }
            
        hwPwCmdAcVlanBindingPrimOrSecondary OBJECT-TYPE
            SYNTAX INTEGER
                {
                primaryPW(1),
                secondaryPW(2)
                }  
            
            MAX-ACCESS not-accessible
            STATUS current
            DESCRIPTION
                "This value indicate Primary PW or Secondary PW.
                 Options:
                 1. primaryPW(1)   -indicates primary PW
                 2. secondaryPW(2) -indicates secondary PW
                "
            ::= { hwPwCmdAcVlanBindingEntry 9 }


        hwPwCmdAcPvpBindingTable OBJECT-TYPE
            SYNTAX SEQUENCE OF HwPwCmdAcPvpBindingEntry
            MAX-ACCESS not-accessible
            STATUS current
            DESCRIPTION
                "This table specifies information for configuring and 
                 status monitoring for PW used in fixed network.
                 The indexes of this table are ifIndex, hwPwCmdAcPvpBindingVpi and hwPwCmdAcPvpBindingPrimOrSecondary.
                "
            ::= { hwPwCmdObjects 11 }
        
        hwPwCmdAcPvpBindingEntry OBJECT-TYPE
            SYNTAX HwPwCmdAcPvpBindingEntry
            MAX-ACCESS not-accessible
            STATUS current
            DESCRIPTION
                "This table specifies information for configuring and 
                 status monitoring for PW used in fixed network.
                 The indexes of this entry are ifIndex, hwPwCmdAcPvpBindingVpi and hwPwCmdAcPvpBindingPrimOrSecondary.
                "
            INDEX { ifIndex, hwPwCmdAcPvpBindingVpi, hwPwCmdAcPvpBindingPrimOrSecondary }
            ::= { hwPwCmdAcPvpBindingTable 1 }
        
        HwPwCmdAcPvpBindingEntry ::=
            SEQUENCE { 
                hwPwCmdAcPvpBindingVpi
                    Unsigned32,
                hwPwCmdAcPvpBindingVcID
                    Unsigned32,  
                hwPwCmdAcPvpBindingVcStatus
                    VcStatusType,
                hwPwCmdAcPvpBindingTemplateName
                    OCTET STRING,       
                hwPwCmdAcPvpBindingOutboundVpi
                    Integer32,
                hwPwCmdAcPvpBindingSignalProtocol
                    SignalProtocolType,
                hwPwCmdAcPvpBindingOutboundLabel
                    Integer32,
                hwPwCmdAcPvpBindingInboundLabel
                    Integer32,
                hwPwCmdAcPvpBindingPrimOrSecondary  
                    INTEGER,
                hwPwCmdAcPvpBindingRowStatus
                    RowStatus
             }

        hwPwCmdAcPvpBindingVpi OBJECT-TYPE
            SYNTAX Unsigned32 (0..4095)
            MAX-ACCESS read-create
            STATUS current
            DESCRIPTION
                "Indicates the VPI value.
                 Range: 0-4095
                "
            ::= { hwPwCmdAcPvpBindingEntry 1 }

        hwPwCmdAcPvpBindingVcID OBJECT-TYPE
            SYNTAX Unsigned32 (1..4294967295)
            MAX-ACCESS read-create
            STATUS current
            DESCRIPTION
                "Used in the outgoing PW ID field within the 'Virtual 
                 Circuit FEC Element'.
                 Range: 1-4294967295
                "
            ::= { hwPwCmdAcPvpBindingEntry 2 }
        
        hwPwCmdAcPvpBindingVcStatus OBJECT-TYPE
            SYNTAX VcStatusType
            MAX-ACCESS read-only
            STATUS current
            DESCRIPTION
                "Indicates the status of the PW: 
                 down(1),
                 up(2),
                 plugout(3).
                "
            ::= { hwPwCmdAcPvpBindingEntry 3 }
        
        hwPwCmdAcPvpBindingTemplateName OBJECT-TYPE
            SYNTAX OCTET STRING (SIZE (1..19))
            MAX-ACCESS read-create
            STATUS current
            DESCRIPTION
                "Indicates the description string of the template,
                 MUST be NULL string if not applicable or not known yet.
                "
            ::= { hwPwCmdAcPvpBindingEntry 4 }

        hwPwCmdAcPvpBindingOutboundVpi OBJECT-TYPE
            SYNTAX Integer32 (0..4095)
            MAX-ACCESS read-create
            STATUS current
            DESCRIPTION
                "Outbound VPI value of this ATM VC.
                 Range: 0-4095
                "
            ::= { hwPwCmdAcPvpBindingEntry 5 }
                
        hwPwCmdAcPvpBindingSignalProtocol OBJECT-TYPE
            SYNTAX SignalProtocolType
            MAX-ACCESS read-create
            STATUS current
            DESCRIPTION
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'rsvp' indicate the use of rsvp  
                 control protocol.
                "
            ::= { hwPwCmdAcPvpBindingEntry 6 }
                    
        hwPwCmdAcPvpBindingOutboundLabel OBJECT-TYPE
            SYNTAX Integer32 (16..1048575)
            MAX-ACCESS read-create
            STATUS current
            DESCRIPTION
                "The PW label used in the outbound direction (i.e. toward  
                 the PSN). 
                 Range: 16-1048575
                 It may be set up manually if owner is 'manual'  
                 or automatically otherwise. Examples: For MPLS PSN, it  
                 represents the 20 bits of PW tag, for L2TP it represent  
                 the 32 bits Session ID. 
                 If the label is not yet known (signaling in process), the  
                 object should return a value of 0xFFFF.
                "
            ::= { hwPwCmdAcPvpBindingEntry 7 }
        
        hwPwCmdAcPvpBindingInboundLabel OBJECT-TYPE
            SYNTAX Integer32 (16..1048575)
            MAX-ACCESS read-create
            STATUS current
            DESCRIPTION
                "The PW label used in the inbound direction (i.e. packets  
                 received from the PSN. 
                 Range: 16-1048575
                 It may be set up manually if owner 
                 is 'manual' or automatically otherwise.  
                 Examples: For MPLS PSN, it represents the 20 bits of PW 
                 tag, for L2TP it represent the 32 bits Session ID. 
                 If the label is not yet known (signaling in process), the  
                 object should return a value of 0xFFFF.
                "
            ::= { hwPwCmdAcPvpBindingEntry 8 }

        hwPwCmdAcPvpBindingPrimOrSecondary OBJECT-TYPE
            SYNTAX INTEGER
                {
                primaryPW(1),
                secondaryPW(2)
                }  
            
            MAX-ACCESS read-create
            STATUS current
            DESCRIPTION
                "This value indicate Primary PW or Secondary PW.
                 Options:
                 1. primaryPW(1)   -indicates primary PW
                 2. secondaryPW(2) -indicates secondary PW
                "
            ::= { hwPwCmdAcPvpBindingEntry 9 }

        hwPwCmdAcPvpBindingRowStatus OBJECT-TYPE
            SYNTAX RowStatus (1..6)
            MAX-ACCESS read-create
            STATUS current
            DESCRIPTION
                "For creating and modifying this row. None of the 
                 read-create objects in the conceptual rows may be changed  
                 when this object is in the active(1) state.
                "
            ::= { hwPwCmdAcPvpBindingEntry 10 }


        hwPwCmdVccvTable OBJECT-TYPE
            SYNTAX SEQUENCE OF HwPwCmdVccvEntry
            MAX-ACCESS not-accessible
            STATUS current
            DESCRIPTION
                "This table specifies information for VCCV ping.
                 The index of this table is hwPwCmdVccvVcID.
                "
            ::= { hwPwCmdObjects 12 }
        
        hwPwCmdVccvEntry OBJECT-TYPE
            SYNTAX HwPwCmdVccvEntry
            MAX-ACCESS not-accessible
            STATUS current
            DESCRIPTION
                "This table specifies information for VCCV ping.
                 The index of this entry is hwPwCmdVccvVcID.
                "
            INDEX { hwPwCmdVccvVcID }
            ::= { hwPwCmdVccvTable 1 }
        
        HwPwCmdVccvEntry ::=
            SEQUENCE { 
                hwPwCmdVccvVcID
                    Unsigned32,
                hwPwCmdVccvReplyMode
                    INTEGER,
                hwPwCmdVccvFrequency
                    INTEGER,
                hwPwCmdVccvTimeoutLimit
                    Unsigned32,
                hwPwCmdVccvRecoverLimit
                    Unsigned32,
                hwPwCmdVccvRemotePwVcID
                    Unsigned32,
                hwPwCmdVccvRemoteIpAddress
                    IpAddress,
                hwPwCmdVccvTtl
                    Unsigned32,
                hwPwCmdVccvPingStatus
                    INTEGER,
                hwPwCmdVccvPingSuccessNum
                    Unsigned32,
                hwPwCmdVccvPingTimeOutNum
                    Unsigned32,
                hwPwCmdVccvRowStatus
                    RowStatus,
                hwPwCmdVccvPingPipeUniform
                    INTEGER
             }               

        hwPwCmdVccvVcID OBJECT-TYPE
            SYNTAX Unsigned32 (1..4294967294)
            MAX-ACCESS read-create
            STATUS current
            DESCRIPTION
                "This value indicate PW ID.
                 Range: 1-4294967294
                "
            ::= { hwPwCmdVccvEntry 1 }
        
        hwPwCmdVccvReplyMode OBJECT-TYPE
            SYNTAX INTEGER
                {
                doNotReply(1),
                replyViaAnIPv4IPv6UdpPacket(2),
                replyViaAnIPv4IPv6UdpPacketWithRouterAlert(3),
                replyViaApplicationLevelControlChannel(4)
                }
            MAX-ACCESS read-write
            STATUS current
            DESCRIPTION
                "The reply mode for the VCCV packet.
                 Options:
                 1. doNotReply(1)                                 -indicates that there is no reply for VCCV PING
                 2. replyViaAnIPv4IPv6UdpPacket(2)                -indicates that reply for VCCV PING using IP UDP packets
                 3. replyViaAnIPv4IPv6UdpPacketWithRouterAlert(3) -indicates that reply for VCCV PING using IP UDP packets with router alert
                 4. replyViaApplicationLevelControlChannel(4)     -indicates that reply for VCCV PING using control channel
                "  
            DEFVAL { replyViaApplicationLevelControlChannel }    
            ::= { hwPwCmdVccvEntry 2 }
                
        hwPwCmdVccvFrequency OBJECT-TYPE
            SYNTAX INTEGER
                {
                freq1000ms(1000),
                freq2000ms(2000),
                freq5000ms(5000),
                freq10000ms(10000)
                }
            MAX-ACCESS read-write
            STATUS current
            DESCRIPTION
                "The frequency of VCCV packet.
                 Options:
                 1. freq1000ms(1000)   -indicates VCCV PING frequency, interval is 1000 ms
                 2. freq2000ms(2000)   -indicates VCCV PING frequency, interval is 2000 ms
                 3. freq5000ms(5000)   -indicates VCCV PING frequency, interval is 5000 ms
                 4. freq10000ms(10000) -indicates VCCV PING frequency, interval is 10000 ms
                " 
            DEFVAL { freq10000ms }
            ::= { hwPwCmdVccvEntry 3 }
        
        hwPwCmdVccvTimeoutLimit OBJECT-TYPE
            SYNTAX Unsigned32 (3..16)
            MAX-ACCESS read-write
            STATUS current
            DESCRIPTION
                "The timeout limit of VCCV ping.
                 Range: 3-16
                " 
            DEFVAL { 3 }
            ::= { hwPwCmdVccvEntry 4 }

        hwPwCmdVccvRecoverLimit OBJECT-TYPE
            SYNTAX Unsigned32 (1..16)
            MAX-ACCESS read-write
            STATUS current
            DESCRIPTION
                "The recover limit of VCCV ping.
                 Range: 1-16
                "
            DEFVAL { 1 }
            ::= { hwPwCmdVccvEntry 5 }

        hwPwCmdVccvRemotePwVcID OBJECT-TYPE
            SYNTAX Unsigned32 (1..4294967295)
            MAX-ACCESS read-write
            STATUS current
            DESCRIPTION
                "Indicates the PW Remote VcID in MH-PW.
                 Range: 1-4294967295.  
                 When this leaf is set to 4294967295, it means that no remote PW ID is configured in the case of no creation, 
                 and that the configuration of remote PW ID is canceled in the case of modify operation.                 
                "
            ::= { hwPwCmdVccvEntry 6 }
                
        hwPwCmdVccvRemoteIpAddress OBJECT-TYPE
            SYNTAX IpAddress
            MAX-ACCESS read-write
            STATUS current
            DESCRIPTION
                "Indicates the PW Remote IP address in MH-PW.
                "
            ::= { hwPwCmdVccvEntry 7 }
                    
        hwPwCmdVccvTtl OBJECT-TYPE
            SYNTAX Unsigned32 (0..255)
            MAX-ACCESS read-write
            STATUS current
            DESCRIPTION
                "Indicates the PW TTL value.
                 Range: 0-255.
                 When this leaf is set to 0, it means that no ttl value is configured in the case of no creation,
                 and that the configuration of TTL value is canceled in the case of modify operation.                 
                "
            ::= { hwPwCmdVccvEntry 8 }

        hwPwCmdVccvPingStatus OBJECT-TYPE
            SYNTAX INTEGER
                {
                normal(0),
                break(1),
                inactive(2)
                }
            MAX-ACCESS read-only
            STATUS current
            DESCRIPTION
                "Indicates the VCCV ping status.
                 Options:
                 1. normal(0)   -indicates that VCCV PING can get reply from the peer and the PW connection is normal
                 2. break(1)    -indicates that VCCV PING cannot reach the peer and the PW connection is break
                 3. inactive(2) -indicates that VCCV PING is not in work mode
                "
            ::= { hwPwCmdVccvEntry 9 }
            
        hwPwCmdVccvPingSuccessNum OBJECT-TYPE
            SYNTAX Unsigned32 (0..4294967295)
            MAX-ACCESS read-only
            STATUS current
            DESCRIPTION
                "The number of VCCV ping succeed.
                 Range: 0-4294967295
                "
            ::= { hwPwCmdVccvEntry 10 }

        hwPwCmdVccvPingTimeOutNum OBJECT-TYPE
            SYNTAX Unsigned32 (0..4294967295)
            MAX-ACCESS read-only
            STATUS current
            DESCRIPTION
                "The number of VCCV ping time out.
                 Range: 0-4294967295
                "
            ::= { hwPwCmdVccvEntry 11 }

        hwPwCmdVccvRowStatus OBJECT-TYPE
            SYNTAX RowStatus (1..6)
            MAX-ACCESS read-write
            STATUS current
            DESCRIPTION
                "For creating and modifying this row. None of the 
                 read-create objects in the conceptual rows may be changed  
                 when this object is in the active(1) state.
                 Options:
                 1. active(1)      -indicates query operation
                 2. createAndGo(4) -indicates creating an auto VCCV PING configuration
                 3. destroy(6)     -indicates deleting an auto VCCV PING configuration
                "
            ::= { hwPwCmdVccvEntry 12 }  
                       
        hwPwCmdVccvPingPipeUniform OBJECT-TYPE
           SYNTAX INTEGER
                { 
                pipe(1),
                uniform(2)       
                }
            MAX-ACCESS read-write
            STATUS current
            DESCRIPTION
                "For setting VCCV ping mode.
                 Options:
                 1. pipe(1)    -indicates pipe mode of the VCCV ping.
                 2. uniform(2) -indicates uniform mode of the VCCV ping. 
                 Default: pipe(1)
                "  
            ::= { hwPwCmdVccvEntry 13 } 


        hwPwCmdRecoverTable OBJECT-TYPE
            SYNTAX SEQUENCE OF HwPwCmdRecoverEntry
            MAX-ACCESS not-accessible
            STATUS current
            DESCRIPTION
                "This table specifies information for recover mode of the PW.
                 The index of this table is hwPwCmdRecoverVcID.
                "
            ::= { hwPwCmdObjects 13 }
        
        hwPwCmdRecoverEntry OBJECT-TYPE
            SYNTAX HwPwCmdRecoverEntry
            MAX-ACCESS not-accessible
            STATUS current
            DESCRIPTION
                "This table specifies information for recover mode of the PW.
                 The index of this entry is hwPwCmdRecoverVcID.
                "
            INDEX { hwPwCmdRecoverVcID }
            ::= { hwPwCmdRecoverTable 1 }
        
        HwPwCmdRecoverEntry ::=
            SEQUENCE { 
                hwPwCmdRecoverVcID
                    Unsigned32,
                hwPwCmdRecoverType
                    INTEGER,
                hwPwCmdRecoverWtrtime
                    Unsigned32
             }

        hwPwCmdRecoverVcID OBJECT-TYPE
            SYNTAX Unsigned32 (1..4294967294)
            MAX-ACCESS not-accessible
            STATUS current
            DESCRIPTION
                "Indicates the PW ID.
                 Range: 1-4294967294
                "
            ::= { hwPwCmdRecoverEntry 1 }
        
        hwPwCmdRecoverType OBJECT-TYPE
            SYNTAX INTEGER
                {
                    revertive(1),
                    nonRevertive(2)
                }          
            MAX-ACCESS read-create
            STATUS current
            DESCRIPTION
                "Indicates the recover mode of the PW.
                 Options:
                 1. revertive(1)    -indicates that automatic recovery is allowed
                 2. nonRevertive(2) -indicates that the traffic will not be switched back to the working PW automatically
                "
            ::= { hwPwCmdRecoverEntry 2 }

        hwPwCmdRecoverWtrtime OBJECT-TYPE
            SYNTAX Unsigned32 (0|10..600)
            MAX-ACCESS read-create
            STATUS current
            DESCRIPTION
                "Indicates the recover time.
                 Range: 0,10-600
                 Unit: second
                "
            ::= { hwPwCmdRecoverEntry 3 }


        hwPwCmdManualSwitchoverTable OBJECT-TYPE
            SYNTAX SEQUENCE OF HwPwCmdManualSwitchoverEntry
            MAX-ACCESS not-accessible
            STATUS current
            DESCRIPTION
                "This table specifies information for manual switchover.
                 The index of this table is hwPwCmdManualSwitchoverVcID.
                "
            ::= { hwPwCmdObjects 14 }

        hwPwCmdManualSwitchoverEntry OBJECT-TYPE
            SYNTAX HwPwCmdManualSwitchoverEntry
            MAX-ACCESS not-accessible
            STATUS current
            DESCRIPTION
                "This table specifies information for manual switchover.
                 The index of this entry is hwPwCmdManualSwitchoverVcID.
                "
            INDEX { hwPwCmdManualSwitchoverVcID }
            ::= { hwPwCmdManualSwitchoverTable 1 }
        
        HwPwCmdManualSwitchoverEntry ::=
            SEQUENCE { 
                hwPwCmdManualSwitchoverVcID
                    Unsigned32,
                hwPwCmdManualSwitchoverSwitchType
                    INTEGER
             }

        hwPwCmdManualSwitchoverVcID OBJECT-TYPE
            SYNTAX Unsigned32 (1..4294967294)
            MAX-ACCESS not-accessible
            STATUS current
            DESCRIPTION
                "Indicates the primary PW ID.
                 Range: 1-4294967294
                "
            ::= { hwPwCmdManualSwitchoverEntry 1 }
        
        hwPwCmdManualSwitchoverSwitchType OBJECT-TYPE
            SYNTAX INTEGER
                {
                primaryPW(1),
                secondaryPW(2)
                }            
            MAX-ACCESS read-create
            STATUS current
            DESCRIPTION
                "Indicates the type of manual switchover.
                 Options:
                 1. primaryPW(1)   -indicates switch from primary PW to secondary PW
                 2. secondaryPW(2) -indicates switch from secondary PW to primary PW
                "
            ::= { hwPwCmdManualSwitchoverEntry 2 }


        hwPwCmdSwitchoverIpAddrTable OBJECT-TYPE
            SYNTAX SEQUENCE OF HwPwCmdSwitchoverIpAddrEntry
            MAX-ACCESS not-accessible
            STATUS current
            DESCRIPTION
                "This table specifies information for 
                 local and remote IP address to switch over.
                 The index of this table is hwPwCmdSwitchoverPwId.
                "
            ::= { hwPwCmdObjects 15 }

        hwPwCmdSwitchoverIpAddrEntry OBJECT-TYPE
            SYNTAX HwPwCmdSwitchoverIpAddrEntry
            MAX-ACCESS not-accessible
            STATUS current
            DESCRIPTION
                "This table specifies information for 
                 local and remote IP address to switch over.
                 The index of this entry is hwPwCmdSwitchoverPwId.
                "
            INDEX { hwPwCmdSwitchoverPwId }
            ::= { hwPwCmdSwitchoverIpAddrTable 1 }
        
        HwPwCmdSwitchoverIpAddrEntry ::=
            SEQUENCE { 
                hwPwCmdSwitchoverPwId
                    Unsigned32,
                hwPwCmdSwitchoverLocalIpAddr
                    IpAddress,
                hwPwCmdSwitchoverRemoteIpAddr
                    IpAddress,
                hwPwCmdSwitchoverRowStatus
                    RowStatus
             }

        hwPwCmdSwitchoverPwId OBJECT-TYPE
            SYNTAX Unsigned32 (1..4294967295)
            MAX-ACCESS read-create
            STATUS current
            DESCRIPTION
                "Indicates the primary PW ID.
                 Range: 1-4294967295
                "
            ::= { hwPwCmdSwitchoverIpAddrEntry 1 }

        hwPwCmdSwitchoverLocalIpAddr OBJECT-TYPE
            SYNTAX IpAddress            
            MAX-ACCESS read-create
            STATUS current
            DESCRIPTION
                "Indicates switch over local IP address of PW.
                "
            ::= { hwPwCmdSwitchoverIpAddrEntry 2 }

        hwPwCmdSwitchoverRemoteIpAddr OBJECT-TYPE
            SYNTAX IpAddress            
            MAX-ACCESS read-create
            STATUS current
            DESCRIPTION
                "Indicates switch over remote IP address of PW.
                "
            ::= { hwPwCmdSwitchoverIpAddrEntry 3 }

        hwPwCmdSwitchoverRowStatus OBJECT-TYPE
            SYNTAX RowStatus (1..6)
            MAX-ACCESS read-create
            STATUS current
            DESCRIPTION
                "For creating and modifying this row. None of the 
                 read-create objects in the conceptual rows may be changed  
                 when this object is in the active(1) state.
                "
            ::= { hwPwCmdSwitchoverIpAddrEntry 4 }
            

        hwPwCmdPsStatusTable OBJECT-TYPE
            SYNTAX SEQUENCE OF HwPwCmdPsStatusEntry
            MAX-ACCESS not-accessible
            STATUS current
            DESCRIPTION
                "This table specifies information for status of PW protect group.
                 The index of this table is hwPwCmdPsPwId.
                "
            ::= { hwPwCmdObjects 16 }

        hwPwCmdPsStatusEntry OBJECT-TYPE
            SYNTAX HwPwCmdPsStatusEntry
            MAX-ACCESS not-accessible
            STATUS current
            DESCRIPTION
                "This table specifies information for status of PW protect group.
                 The index of this entry is hwPwCmdPsPwId.
                "
            INDEX { hwPwCmdPsPwId }
            ::= { hwPwCmdPsStatusTable 1 }
        
        HwPwCmdPsStatusEntry ::=
            SEQUENCE { 
                hwPwCmdPsPwId
                    Unsigned32,
                hwPwCmdPsPrimaryPwStatus
                    INTEGER,
                hwPwCmdPsSecondaryPwStatus
                    INTEGER
             }

        hwPwCmdPsPwId OBJECT-TYPE
            SYNTAX Unsigned32 (1..4294967294)
            MAX-ACCESS not-accessible
            STATUS current
            DESCRIPTION
                "Indicates the primary PW ID.
                 Range: 1-4294967294
                "
            ::= { hwPwCmdPsStatusEntry 1 }

        hwPwCmdPsPrimaryPwStatus OBJECT-TYPE
            SYNTAX INTEGER
                {
                    down(1),
                    upActive(2),
                    upStandby(3)
                }
            MAX-ACCESS read-only
            STATUS current
            DESCRIPTION
                "Indicates status of primary PW.
                 Options:
                 1. down(1)      -indicates that the primary member of the PW protect group is down
                 2. upActive(2)  -indicates that the primary member of the PW protect group is up and active
                 3. upStandby(3) -indicates that the primary member of the PW protect group is up and standby
                "
            ::= { hwPwCmdPsStatusEntry 2 }

        hwPwCmdPsSecondaryPwStatus OBJECT-TYPE
            SYNTAX INTEGER
                {
                    down(1),
                    upActive(2),
                    upStandby(3)
                }            
            MAX-ACCESS read-only
            STATUS current
            DESCRIPTION
                "Indicates status of secondary PW.
                 Options:
                 1. down(1)      -indicates that the secondary member of the PW protect group is down
                 2. upActive(2)  -indicates that the secondary member of the PW protect group is up and active
                 3. upStandby(3) -indicates that the secondary member of the PW protect group is up and standby                     
                "
            ::= { hwPwCmdPsStatusEntry 3 }           


        hwPwCmdPvcExpMapTable OBJECT-TYPE
            SYNTAX SEQUENCE OF HwPwCmdPvcExpMapEntry
            MAX-ACCESS not-accessible
            STATUS current
            DESCRIPTION
                "This table specifies information for PVC-EXP mapping.
                 The indexes of this table are ifIndex, hwPwCmdPvcExpMapVpi, hwPwCmdPvcExpMapVci.
                "
            ::= { hwPwCmdObjects 17 }

        hwPwCmdPvcExpMapEntry OBJECT-TYPE
            SYNTAX HwPwCmdPvcExpMapEntry
            MAX-ACCESS not-accessible
            STATUS current
            DESCRIPTION
                "This table specifies information for PVC-EXP mapping.
                 The indexes of this entry are ifIndex, hwPwCmdPvcExpMapVpi, hwPwCmdPvcExpMapVci.
                "
            INDEX { ifIndex, hwPwCmdPvcExpMapVpi, hwPwCmdPvcExpMapVci }
            ::= { hwPwCmdPvcExpMapTable 1 }
        
        HwPwCmdPvcExpMapEntry ::=
            SEQUENCE {
                hwPwCmdPvcExpMapVpi
                    Unsigned32,
                hwPwCmdPvcExpMapVci
                    Unsigned32,
                hwPwCmdPvcExpMapExp
                    Unsigned32,
                hwPwCmdPvcExpMapRowStatus
                    RowStatus
             }
            
        hwPwCmdPvcExpMapVpi OBJECT-TYPE
            SYNTAX Unsigned32 (0..4095)
            MAX-ACCESS read-create
            STATUS current
            DESCRIPTION
                "Indicates the VPI value.
                 Range: 0-4095
                "
            ::= { hwPwCmdPvcExpMapEntry 1 }

        hwPwCmdPvcExpMapVci OBJECT-TYPE
            SYNTAX Unsigned32 (32..65535)
            MAX-ACCESS read-create
            STATUS current
            DESCRIPTION
                "Indicates the VCI value.
                 Range: 32-65535
                "
            ::= { hwPwCmdPvcExpMapEntry 2 }

        hwPwCmdPvcExpMapExp OBJECT-TYPE
            SYNTAX Unsigned32 (0..7)
            MAX-ACCESS read-create
            STATUS current
            DESCRIPTION
                "Indicates the EXP value.
                 Range: 0-7
                "
            ::= { hwPwCmdPvcExpMapEntry 3 }

        hwPwCmdPvcExpMapRowStatus OBJECT-TYPE
            SYNTAX RowStatus (1..6)
            MAX-ACCESS read-create
            STATUS current
            DESCRIPTION
                "For creating and modifying this row. None of the 
                 read-create objects in the conceptual rows may be changed  
                 when this object is in the active(1) state.
                 Options:
                 1. active(1)      -indicates query operation
                 2. createAndGo(4) -indicates creating a mapping from PVC to MPLS EXP
                 3. destroy(6)     -indicates deleting a mapping from PVC to MPLS EXP
                "
            ::= { hwPwCmdPvcExpMapEntry 4 }


        hwPwCmdExpCosMapTable OBJECT-TYPE
            SYNTAX SEQUENCE OF HwPwCmdExpCosMapEntry
            MAX-ACCESS not-accessible
            STATUS current
            DESCRIPTION
                "This table specifies information for EXP-COS mapping.
                 The index of this table is hwPwCmdExpCosMapExp.
                "
            ::= { hwPwCmdObjects 18 }

        hwPwCmdExpCosMapEntry OBJECT-TYPE
            SYNTAX HwPwCmdExpCosMapEntry
            MAX-ACCESS not-accessible
            STATUS current
            DESCRIPTION
                "This table specifies information for EXP-COS mapping.
                 The index of this entry is hwPwCmdExpCosMapExp.
                "
            INDEX { hwPwCmdExpCosMapExp }
            ::= { hwPwCmdExpCosMapTable 1 }
        
        HwPwCmdExpCosMapEntry ::=
            SEQUENCE { 
                hwPwCmdExpCosMapExp
                    Unsigned32,
                hwPwCmdExpCosMapCos
                    Unsigned32
             }

        hwPwCmdExpCosMapExp OBJECT-TYPE
            SYNTAX Unsigned32 (0..7)
            MAX-ACCESS read-create
            STATUS current
            DESCRIPTION
                "Indicates the EXP value.
                 Range: 0-7
                "
            ::= { hwPwCmdExpCosMapEntry 1 }

        hwPwCmdExpCosMapCos OBJECT-TYPE
            SYNTAX Unsigned32 (0..7)
            MAX-ACCESS read-create
            STATUS current
            DESCRIPTION
                "Indicates the COS value.
                 Range: 0-7
                "
            ::= { hwPwCmdExpCosMapEntry 2 }

        hwPwCmdTdmExpMapTable OBJECT-TYPE
            SYNTAX SEQUENCE OF HwPwCmdTdmExpMapEntry
            MAX-ACCESS not-accessible
            STATUS current
            DESCRIPTION
                "This table specifies information for TDM-EXP mapping.
                 The index of this table is hwPwCmdTdmConnectId.
                "
            ::= { hwPwCmdObjects 19 }
            
        hwPwCmdTdmExpMapEntry OBJECT-TYPE
            SYNTAX HwPwCmdTdmExpMapEntry
            MAX-ACCESS not-accessible
            STATUS current
            DESCRIPTION
                "This table specifies information for TDM-EXP mapping.
                 The index of this entry is hwPwCmdTdmConnectId.
                "
            INDEX { hwPwCmdTdmConnectId }
            ::= { hwPwCmdTdmExpMapTable 1 }
            
        HwPwCmdTdmExpMapEntry ::=
            SEQUENCE { 
                hwPwCmdTdmConnectId
                    Unsigned32,
                hwPwCmdTdmExpMapExp
                    Unsigned32,
                hwPwCmdTdmExpMapRowStatus
                    RowStatus    
             }
        
        hwPwCmdTdmConnectId OBJECT-TYPE
            SYNTAX Unsigned32 (0..2047)
            MAX-ACCESS read-write
            STATUS current
            DESCRIPTION
                "Indicates the TDM connect ID.
                 Range: 0-2047
                "
            ::= { hwPwCmdTdmExpMapEntry 1 }
                    
        hwPwCmdTdmExpMapExp OBJECT-TYPE
            SYNTAX Unsigned32 (0..7)
            MAX-ACCESS read-write
            STATUS current
            DESCRIPTION
                "Indicates the EXP value.
                 Range: 0-7
                 Default: 0
                    "
            DEFVAL { 0 }
            ::= { hwPwCmdTdmExpMapEntry 2 }      
                
        hwPwCmdTdmExpMapRowStatus OBJECT-TYPE
            SYNTAX RowStatus (1..6)
            MAX-ACCESS read-create
            STATUS current
            DESCRIPTION
                "For creating and modifying this row. None of the 
                 read-create objects in the conceptual rows may be changed  
                 when this object is in the active(1) state.
                 Options:
                 1. active(1)      -indicates query operation
                 2. createAndGo(4) -indicates creating a mapping from TDM to MPLS EXP
                 3. destroy(6)     -indicates deleting a mapping from TDM to MPLS EXP
                "
            ::= { hwPwCmdTdmExpMapEntry 3 }
                    
        hwPwCmdAcTdmBindingTable OBJECT-TYPE
            SYNTAX SEQUENCE OF HwPwCmdAcTdmBindingEntry
            MAX-ACCESS not-accessible
            STATUS current
            DESCRIPTION
                "This table specifies information for configuring and 
                 status monitoring for PW used in fixed network.
                 The indexes of this table are hwPwCmdAcTdmBindingTdmConnectId and hwPwCmdAcTdmBindingPrimOrSecondary.
                "
            ::= { hwPwCmdObjects 20 }
            
        hwPwCmdAcTdmBindingEntry OBJECT-TYPE
            SYNTAX HwPwCmdAcTdmBindingEntry
            MAX-ACCESS not-accessible
            STATUS current
            DESCRIPTION
                "This table specifies information for configuring and 
                 status monitoring for PW used in fixed network.
                 The indexes of this entry are hwPwCmdAcTdmBindingTdmConnectId and hwPwCmdAcTdmBindingPrimOrSecondary.
                "
            INDEX { hwPwCmdAcTdmBindingTdmConnectId, hwPwCmdAcTdmBindingPrimOrSecondary}
            ::= { hwPwCmdAcTdmBindingTable 1 }

        HwPwCmdAcTdmBindingEntry ::=
            SEQUENCE { 
                hwPwCmdAcTdmBindingTdmConnectId
                    Unsigned32,
                hwPwCmdAcTdmBindingVcID
                    Unsigned32,  
                hwPwCmdAcTdmBindingVcStatus
                    VcStatusType,
                hwPwCmdAcTdmBindingTemplateName
                    OCTET STRING,  
                hwPwCmdAcTdmBindingEncapUDPPort
                    Integer32,     
                hwPwCmdAcTdmBindingSignalProtocol
                    SignalProtocolType,
                hwPwCmdAcTdmBindingOutboundLabel
                    Integer32,
                hwPwCmdAcTdmBindingInboundLabel
                    Integer32,
                hwPwCmdAcTdmBindingPrimOrSecondary   
                    INTEGER,
                hwPwCmdAcTdmBindingRowStatus
                    RowStatus
            }
        
        hwPwCmdAcTdmBindingTdmConnectId OBJECT-TYPE
            SYNTAX Unsigned32 (0..1023)
            MAX-ACCESS read-write
            STATUS current
            DESCRIPTION
                "Indicates the connect index referenced.
                 Range: 0-1023
                "
            ::= { hwPwCmdAcTdmBindingEntry 1 }  
            
        hwPwCmdAcTdmBindingVcID OBJECT-TYPE  
            SYNTAX Unsigned32 (1..4294967294)
            MAX-ACCESS read-write              
            STATUS current                     
            DESCRIPTION                        
                "Used in the outgoing PW ID field within the 'Virtual 
                 Circuit FEC Element'.
                 Range: 1-4294967294
                "                   
            ::= { hwPwCmdAcTdmBindingEntry 2 } 
            
        hwPwCmdAcTdmBindingVcStatus OBJECT-TYPE
            SYNTAX VcStatusType
            MAX-ACCESS read-write
            STATUS current
            DESCRIPTION
                "Indicates the status of the PW: 
                 down(1),
                 up(2),
                 plugout(3).
                "
            ::= { hwPwCmdAcTdmBindingEntry 3 }
            
        hwPwCmdAcTdmBindingTemplateName OBJECT-TYPE
            SYNTAX OCTET STRING (SIZE (1..19))
            MAX-ACCESS read-write
            STATUS current
            DESCRIPTION
                "Indicates the description string of the template,
                 MUST be NULL string if not applicable or not known yet.
                "
            ::= { hwPwCmdAcTdmBindingEntry 4 }
            
        hwPwCmdAcTdmBindingEncapUDPPort OBJECT-TYPE
            SYNTAX Integer32 (50000..57300)
            MAX-ACCESS read-write
            STATUS current
            DESCRIPTION
                "Indicates UDP protocol encapsulation, UDP destination port.
                 Range: 50000-57300
                "
            ::= { hwPwCmdAcTdmBindingEntry 5 }
            
        hwPwCmdAcTdmBindingSignalProtocol OBJECT-TYPE
            SYNTAX SignalProtocolType
            MAX-ACCESS read-write
            STATUS current
            DESCRIPTION
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'rsvp' indicate the use of rsvp  
                 control protocol.
                "
            ::= { hwPwCmdAcTdmBindingEntry 6 }
            
        hwPwCmdAcTdmBindingOutboundLabel OBJECT-TYPE
            SYNTAX Integer32 (16..1048575)
            MAX-ACCESS read-write
            STATUS current
            DESCRIPTION
                "The PW label used in the outbound direction (i.e. toward  
                 the PSN). 
                 Range: 16-1048575
                 It may be set up manually if owner is 'manual'  
                 or automatically otherwise. Examples: For MPLS PSN, it  
                 represents the 20 bits of PW tag, for L2TP it represent  
                 the 32 bits Session ID. 
                 If the label is not yet known (signaling in process), the  
                 object should return a value of 0xFFFF.
                "
            ::= { hwPwCmdAcTdmBindingEntry 7 }
            
        hwPwCmdAcTdmBindingInboundLabel OBJECT-TYPE
            SYNTAX Integer32 (16..1048575)
            MAX-ACCESS read-write
            STATUS current
            DESCRIPTION
                "The PW label used in the inbound direction (i.e. packets  
                 received from the PSN. 
                 Range: 16-1048575
                 It may be set up manually if owner 
                 is 'manual' or automatically otherwise.  
                 Examples: For MPLS PSN, it represents the 20 bits of PW 
                 tag, for L2TP it represent the 32 bits Session ID. 
                 If the label is not yet known (signaling in process), the  
                 object should return a value of 0xFFFF.
                "
            ::= { hwPwCmdAcTdmBindingEntry 8 }
            
        hwPwCmdAcTdmBindingPrimOrSecondary OBJECT-TYPE
            SYNTAX INTEGER
                {
                primaryPW(1),
                secondaryPW(2)
                }  
            MAX-ACCESS read-write                 
            STATUS current                        
            DESCRIPTION                           
                "This value indicate Primary PW or Secondary PW.
                 Options:
                 1. primaryPW(1)   -indicates primary PW
                 2. secondaryPW(2) -indicates secondary PW
                "                      
            ::= { hwPwCmdAcTdmBindingEntry 9 }  
                    
        hwPwCmdAcTdmBindingRowStatus OBJECT-TYPE                                      
            SYNTAX RowStatus (1..6)
            MAX-ACCESS read-write                 
            STATUS current                        
            DESCRIPTION                           
                "For creating and modifying this row. None of the 
                 read-create objects in the conceptual rows may be changed  
                 when this object is in the active(1) state.
                "                      
            ::= { hwPwCmdAcTdmBindingEntry 10 } 
                 
        hwPwCmdPwTable OBJECT-TYPE
            SYNTAX SEQUENCE OF HwPwCmdPwEntry
            MAX-ACCESS not-accessible
            STATUS current
            DESCRIPTION
                "This table specifies information for configuring and 
                 status monitoring for PW used in fixed network.
                 The index of this table is hwPwCmdPwID.
                "
            ::= { hwPwCmdObjects 21 }
            
        hwPwCmdPwEntry OBJECT-TYPE
            SYNTAX HwPwCmdPwEntry
            MAX-ACCESS not-accessible
            STATUS current
            DESCRIPTION
                "This table specifies information for configuring and 
                 status monitoring for PW used in fixed network.
                 The index of this entry is hwPwCmdPwID.
                "
            INDEX {hwPwCmdPwID}
            ::= { hwPwCmdPwTable 1 }
            
        HwPwCmdPwEntry ::=
            SEQUENCE { 
                hwPwCmdPwID
                    Unsigned32,
                hwPwCmdPwTemplateName
                    OCTET STRING,
                hwPwCmdPwAcBindMode
                    INTEGER,
                hwPwCmdPwVlanID
                    Unsigned32,
                hwPwCmdPwTdmVclID
                    Unsigned32,
                hwPwCmdPwIfindex
                    Integer32,
                hwPwCmdPwVci
                    Integer32,
                hwPwCmdPwVpi
                    Integer32,
                hwPwCmdPwOutboundVci
                    Integer32,
                hwPwCmdPwOutboundVpi
                    Integer32,
                hwPwCmdPwImaGroup
                    Unsigned32,
                hwPwCmdPwVcStatus
                    VcStatusType,
                hwPwCmdPwEncapSrcUDPPort
                    Integer32,
                hwPwCmdPwEncapDstUDPPort
                    Integer32,
                hwPwCmdPwSignalProtocol
                    SignalProtocolType,
                hwPwCmdPwOutboundLabel
                    Integer32,
                hwPwCmdPwInboundLabel
                    Unsigned32,
                hwPwCmdPwPriority
                    INTEGER,
                hwPwCmdPwRowStatus
                    RowStatus,
                hwPwCmdPwDesc
                    OCTET STRING,
                hwPwCmdPwReceiveDstUDPPort
                    Integer32,
                hwPwCmdPwMultiPvc
                    OCTET STRING,
                hwPwCmdPwMultiPvcOp
                    INTEGER                        
                }
                
        hwPwCmdPwID OBJECT-TYPE
            SYNTAX Unsigned32 (1..4294967294)
            MAX-ACCESS read-write
            STATUS current
            DESCRIPTION
                "Used in the outgoing PW ID field within the 'Virtual 
                 Circuit FEC Element'.
                 Range: 1-4294967294
                "
            ::= { hwPwCmdPwEntry 1 }
                
        hwPwCmdPwTemplateName OBJECT-TYPE
            SYNTAX OCTET STRING (SIZE (1..19))
            MAX-ACCESS read-create
            STATUS current
            DESCRIPTION
                "Indicates the description string of the template,
                 MUST be NULL string if not applicable or not known yet.
                "
            ::= { hwPwCmdPwEntry 2 }
                
        hwPwCmdPwAcBindMode OBJECT-TYPE
            SYNTAX INTEGER
                {
                vlan(1),
                tdm(2),
                pvcfsp(3),
                pvpfsp(4)
                }
            MAX-ACCESS read-write
            STATUS current
            DESCRIPTION
                "AcType.
                 Options:
                 1. vlan(1)   -indicates vlan
                 2. tdm(2)    -indicates tdm 
                 3. pvcfsp(3) -indicates pvc fsp
                 4. pvpfsp(4) -indicates pvp fsp                
                "
            ::= { hwPwCmdPwEntry 3 }
                                    
        hwPwCmdPwVlanID OBJECT-TYPE
            SYNTAX Unsigned32 (2..4093)
            MAX-ACCESS not-accessible
            STATUS current
            DESCRIPTION
                "Indicates the VLAN ID referenced.
                 Range: 2-4093
                "
            ::= { hwPwCmdPwEntry 4 }  
                  
        hwPwCmdPwTdmVclID OBJECT-TYPE
            SYNTAX Unsigned32 (0..2047|4294967295)
            MAX-ACCESS read-write
            STATUS current
            DESCRIPTION
                "Indicates the connect index referenced.
                 Range: 0-2047, 4294967295
                "
            ::= { hwPwCmdPwEntry 5 }                                                  
        
        hwPwCmdPwIfindex OBJECT-TYPE
            SYNTAX Integer32 (-1|1..2147483647)
            MAX-ACCESS read-create
            STATUS current
            DESCRIPTION
                "Index of the interface (or the virtual interface) 
                 associated with the PW.
                 Range: 1-2147483647, -1
                "
            ::= { hwPwCmdPwEntry 6 }

        hwPwCmdPwVci OBJECT-TYPE
            SYNTAX Integer32 (-1|32..65535)
            MAX-ACCESS read-create
            STATUS current
            DESCRIPTION
                "Indicates the VPI value.
                 Range: 32-65535, -1
                "
            ::= { hwPwCmdPwEntry 7 }
        
        hwPwCmdPwVpi OBJECT-TYPE
            SYNTAX Integer32 (-1|0..4095)
            MAX-ACCESS read-create
            STATUS current
            DESCRIPTION
                "Used in the outgoing PW ID field within the 'Virtual 
                 Circuit FEC Element'.
                 Range: 0-4095, -1
                "
            ::= { hwPwCmdPwEntry 8 }
        
        hwPwCmdPwOutboundVci OBJECT-TYPE
            SYNTAX Integer32 (-1|32..65535)
            MAX-ACCESS read-create
            STATUS current
            DESCRIPTION
                "VCI value of this ATM VC. 
                 Range: 32-65535, -1
                 If the pwVcType is atmNto1Transparent, atmCell1to1Vpc or
                 atmCellNto1Vpc then the value should be set to zero.
                "
            ::= { hwPwCmdPwEntry 9 }
        
        hwPwCmdPwOutboundVpi OBJECT-TYPE
            SYNTAX Integer32 (-1|0..4095)
            MAX-ACCESS read-create
            STATUS current
            DESCRIPTION
                "VPI value of this ATM VC. 
                 Range: 0-4095, -1
                 If the pwVcType is atmNto1Transparent then the value will be set
                 to zero.
                "
            ::= { hwPwCmdPwEntry 10 }
 
        hwPwCmdPwImaGroup OBJECT-TYPE
            SYNTAX Unsigned32 (0..4294967294)
            MAX-ACCESS not-accessible
            STATUS current
            DESCRIPTION
                "Indicates the VLAN ID referenced.
                 Range: 0-4294967294
                "
            ::= { hwPwCmdPwEntry 11 }                   
  
        hwPwCmdPwVcStatus OBJECT-TYPE
            SYNTAX VcStatusType
            MAX-ACCESS read-only
            STATUS current
            DESCRIPTION
                "Indicates the status of the PW: 
                 down(1),
                 up(2),
                 plugout(3).
                "
            ::= { hwPwCmdPwEntry 12 }                
            
        hwPwCmdPwEncapSrcUDPPort OBJECT-TYPE
            SYNTAX Integer32 (-1|50000..57300)
            MAX-ACCESS read-write
            STATUS current
            DESCRIPTION
                "Indicates UDP protocol encapsulation, UDP destination port.
                 Range: 50000-57300, -1
                "
            ::= { hwPwCmdPwEntry 13 }
            
        hwPwCmdPwEncapDstUDPPort OBJECT-TYPE
            SYNTAX Integer32 (-1|49152..65535)
            MAX-ACCESS read-write
            STATUS current
            DESCRIPTION
                "Indicates UDP protocol encapsulation, UDP destination port.
                 Range: 49152-65535, -1
                "
            ::= { hwPwCmdPwEntry 14 }
                
        hwPwCmdPwSignalProtocol OBJECT-TYPE
            SYNTAX SignalProtocolType
            MAX-ACCESS read-create
            STATUS current
            DESCRIPTION
                "Set by the operator to indicate the protocol responsible  
                 for establishing this PW. The value 'static' is used in all 
                 cases where no maintenance protocol (PW signaling) is used  
                 to set up the PW, i.e. require configuration of entries in 
                 the PW tables including PW labels, etc. The value 'ldp' is 
                 used in case of signaling with the Pwid FEC element with LDP 
                 signaling. The value 'rsvp' indicate the use of rsvp  
                 control protocol.
                "
            ::= { hwPwCmdPwEntry 15 }
            
        hwPwCmdPwOutboundLabel OBJECT-TYPE
            SYNTAX Integer32 (-1|16..1048575)
            MAX-ACCESS read-create
            STATUS current
            DESCRIPTION
                "The PW label used in the outbound direction (i.e. toward  
                 the PSN).
                 Range: 16-1048575, -1
                 It may be set up manually if owner is 'manual'  
                 or automatically otherwise. Examples: For MPLS PSN, it  
                 represents the 20 bits of PW tag, for L2TP it represent  
                 the 32 bits Session ID. 
                 If the label is not yet known (signaling in process), the  
                 object should return a value of 0xFFFF.
                "
            ::= { hwPwCmdPwEntry 16 } 
        
        hwPwCmdPwInboundLabel OBJECT-TYPE
            SYNTAX Unsigned32 (16..1048575)
            MAX-ACCESS read-create
            STATUS current
            DESCRIPTION
                "The PW label used in the inbound direction (i.e. packets  
                 received from the PSN. 
                 Range: 16-1048575
                 It may be set up manually if owner 
                 is 'manual' or automatically otherwise.  
                 Examples: For MPLS PSN, it represents the 20 bits of PW 
                 tag, for L2TP it represent the 32 bits Session ID. 
                 If the label is not yet known (signaling in process), the  
                 object should return a value of 0xFFFF.
                "
            ::= { hwPwCmdPwEntry 17 }
            
        hwPwCmdPwPriority OBJECT-TYPE
            SYNTAX INTEGER
                {
                primaryPW(1),
                secondaryPW(2)
                }  
            MAX-ACCESS read-write                 
            STATUS current                        
            DESCRIPTION                           
                "This value indicate Primary PW or Secondary PW.
                 Options:
                 1. primaryPW(1)   -indicates primary PW
                 2. secondaryPW(2) -indicates secondary PW
                "                      
            ::= { hwPwCmdPwEntry 18 }
                
        hwPwCmdPwRowStatus OBJECT-TYPE                                      
            SYNTAX RowStatus (1..6)
            MAX-ACCESS read-write                 
            STATUS current                        
            DESCRIPTION                           
                "For creating and modifying this row. None of the 
                 read-create objects in the conceptual rows may be changed  
                 when this object is in the active(1) state.
                "                      
            ::= { hwPwCmdPwEntry 19 }  
                

        hwPwCmdPwDesc OBJECT-TYPE
            SYNTAX OCTET STRING (SIZE (0..32))
            MAX-ACCESS read-write
            STATUS current
            DESCRIPTION
                "PW description, used to describe extra information of PW.
                "
            ::= { hwPwCmdPwEntry 20 }
            
        hwPwCmdPwReceiveDstUDPPort OBJECT-TYPE
            SYNTAX Integer32 (-1|50048..50111)
            MAX-ACCESS read-write
            STATUS current
            DESCRIPTION
                "Indicates UDP protocol encapsulation, UDP source port.
                 Range: 50048-50111, -1
                "
            ::= { hwPwCmdPwEntry 21 }
                                
        hwPwCmdPwMultiPvc OBJECT-TYPE
            SYNTAX OCTET STRING (SIZE (0..800))
            MAX-ACCESS read-write
            STATUS current
            DESCRIPTION
                "Multi VCCs or VPCs string, include vpi,vci,outvpi and outvci.
                "
            ::= { hwPwCmdPwEntry 22 }
                               
        hwPwCmdPwMultiPvcOp OBJECT-TYPE
            SYNTAX INTEGER
                {
                add(1),
                delete(2),
                invalidValue(-1)
                }  
            MAX-ACCESS read-write                 
            STATUS current                        
            DESCRIPTION                           
                "Multi VCCs or VPCs operate code, add or delete.
                 Options:
                 1. add(1)           -indicates add operation
                 2. delete(2)        -indicates delete operation
                 3. invalidValue(-1) -indicates invalid value
                "                      
            ::= { hwPwCmdPwEntry 23 }
            
        hwPwCmdPwCarTable OBJECT-TYPE
            SYNTAX SEQUENCE OF HwPwCmdPwCarEntry
            MAX-ACCESS not-accessible
            STATUS current
            DESCRIPTION
                "This table specifies information for PW CAR.
                 The index of this table is hwPwCmdPWCarVcID.
                "
            ::= { hwPwCmdObjects 22 }
            
        hwPwCmdPwCarEntry OBJECT-TYPE
            SYNTAX HwPwCmdPwCarEntry
            MAX-ACCESS not-accessible
            STATUS current
            DESCRIPTION
                "This table specifies information for PW CAR.
                 The index of this entry is hwPwCmdPWCarVcID.
                "
            INDEX { hwPwCmdPWCarVcID }
            ::= { hwPwCmdPwCarTable 1 }
            
        HwPwCmdPwCarEntry ::=
            SEQUENCE { 
                hwPwCmdPWCarVcID
                    Unsigned32,
                hwPwCmdPWCarCir
                    Unsigned32,
                hwPwCmdPWCarCbs
                    Unsigned32,
                hwPwCmdPWCarPir
                    Unsigned32,
                hwPwCmdPWCarPbs
                    Unsigned32,                       
                hwPwCmdPWCarRowStatus
                    RowStatus    
             }
        
        hwPwCmdPWCarVcID OBJECT-TYPE
            SYNTAX Unsigned32 (1..4294967294)
            MAX-ACCESS not-accessible
            STATUS current
            DESCRIPTION
                "Indicates the PW ID.
                 Range: 1-4294967294
                "
            ::= { hwPwCmdPwCarEntry 1 }
                
        hwPwCmdPWCarRowStatus OBJECT-TYPE
            SYNTAX RowStatus (1..6)
            MAX-ACCESS read-create
            STATUS current
            DESCRIPTION
                "For creating and modifying this row. None of the 
                 read-create objects in the conceptual rows may be changed  
                 when this object is in the active(1) state.
                 Options:
                 1. active(1)      -indicates query operation
                 2. createAndGo(4) -indicates creating committed access rate parameters of a PW
                 3. destroy(6)     -indicates deleting committed access rate parameters of a PW
                "
            ::= { hwPwCmdPwCarEntry 4 }
            
        hwPwCmdPWCarCir OBJECT-TYPE
            SYNTAX Unsigned32 (1..1048575)
            MAX-ACCESS read-write
            STATUS current
            DESCRIPTION
                "Committed information rate, it is the necessary parameter for adding pw car.
                 Range: 1-1048575 
                 Unit: 64Kbit/s
                "
            ::= { hwPwCmdPwCarEntry 5 }  
                            
        hwPwCmdPWCarCbs OBJECT-TYPE
            SYNTAX Unsigned32 (1..32767)
            MAX-ACCESS read-write
            STATUS current
            DESCRIPTION
                "Committed burst size, default value is ((cir+8191)/8192+1).
                 Range: 1-32767 
                 Unit: 2KByte/s
                "
            ::= { hwPwCmdPwCarEntry 6 } 
            
        hwPwCmdPWCarPir OBJECT-TYPE
            SYNTAX Unsigned32 (1..1048575)
            MAX-ACCESS read-write
            STATUS current
            DESCRIPTION
                "Peak information rate, default value is double of committed information rate.
                 Range: 1-1048575 
                 Unit: 64Kbit/s
                "
            ::= { hwPwCmdPwCarEntry 7 }  
                            
        hwPwCmdPWCarPbs OBJECT-TYPE
            SYNTAX Unsigned32 (1..32767)
            MAX-ACCESS read-write
            STATUS current
            DESCRIPTION
                "Peak burst size, default value is MAX(((pir+8191)/8192 + 1), cbs).
                 Range: 1-32767 
                 Unit: 2KByte/s
                "
            ::= { hwPwCmdPwCarEntry 8 }  
  
        hwPwCmdPvpExpMapTable OBJECT-TYPE
            SYNTAX SEQUENCE OF HwPwCmdPvpExpMapEntry
            MAX-ACCESS not-accessible
            STATUS current
            DESCRIPTION
                "This table specifies information for PVP-EXP mapping.
                 The indexes of this table are ifIndex and hwPwCmdPvpExpMapVpi.
                "
            ::= { hwPwCmdObjects 23 }

        hwPwCmdPvpExpMapEntry OBJECT-TYPE
            SYNTAX HwPwCmdPvpExpMapEntry
            MAX-ACCESS not-accessible
            STATUS current
            DESCRIPTION
                "This table specifies information for PVP-EXP mapping.
                 The indexes of this entry are ifIndex and hwPwCmdPvpExpMapVpi.
                "
            INDEX { ifIndex, hwPwCmdPvpExpMapVpi }
            ::= { hwPwCmdPvpExpMapTable 1 }
        
        HwPwCmdPvpExpMapEntry ::=
            SEQUENCE {
                hwPwCmdPvpExpMapVpi
                    Unsigned32,
                hwPwCmdPvpExpMapExp
                    Unsigned32,
                hwPwCmdPvpExpMapRowStatus
                    RowStatus
             }
            
        hwPwCmdPvpExpMapVpi OBJECT-TYPE
            SYNTAX Unsigned32 (0..4095)
            MAX-ACCESS read-create
            STATUS current
            DESCRIPTION
                "Indicates the VPI value.
                 Range: 0-4095
                "
            ::= { hwPwCmdPvpExpMapEntry 1 }

        hwPwCmdPvpExpMapExp OBJECT-TYPE
            SYNTAX Unsigned32 (0..7)
            MAX-ACCESS read-create
            STATUS current
            DESCRIPTION
                "Indicates the EXP value.
                 Range: 0-7
                "
            ::= { hwPwCmdPvpExpMapEntry 2 }

        hwPwCmdPvpExpMapRowStatus OBJECT-TYPE
            SYNTAX RowStatus (1..6)
            MAX-ACCESS read-create
            STATUS current
            DESCRIPTION
                "For creating and modifying this row. None of the 
                 read-create objects in the conceptual rows may be changed  
                 when this object is in the active(1) state.
                 Options:
                 1. active(1)      -indicates query operation
                 2. createAndGo(4) -indicates creating a mapping from PVP to MPLS EXP
                 3. destroy(6)     -indicates deleting a mapping from PVP to MPLS EXP
                "
            ::= { hwPwCmdPvpExpMapEntry 3 }
        

        hwMplsEcmpEnable OBJECT-TYPE
            SYNTAX INTEGER
                {
                    enable(1),
                    disable(2)
                }
            MAX-ACCESS read-write
            STATUS current
            DESCRIPTION
                "Used to enable or disable the ECMP function. 
                 Options:
                 1. enable(1)  -indicates that the ECMP function is enabled
                 2. disable(2) -indicates that the ECMP function is disabled
                 Default: disable(2)
                " 
            ::= { hwPwCmdObjects 24 }


        hwMplsL2VPNEnable OBJECT-TYPE
            SYNTAX INTEGER
                {
                    enable(1),
                    disable(2)
                }
            MAX-ACCESS read-write
            STATUS current
            DESCRIPTION
                "Used to enable or disable the MPLS L2VPN function.
                 Options:
                 1. enable(1)  -indicates that the MPLS L2VPN function is enabled
                 2. disable(2) -indicates that the MPLS L2VPN function is disabled
                 Default: disable(2)
                " 
            ::= { hwPwCmdObjects 25 }

        
        hwPwExtTable OBJECT-TYPE
            SYNTAX SEQUENCE OF HwPwExtEntry
            MAX-ACCESS not-accessible
            STATUS current
            DESCRIPTION
                "This table specifies the extend information for configuring and
                 status monitoring that are common to all service types
                 and PSN types.
                 The index of this table is pwIndex.
                "
            ::= { hwPwCmdObjects 26 }

        hwPwExtEntry   OBJECT-TYPE
            SYNTAX        HwPwExtEntry
            MAX-ACCESS    not-accessible
            STATUS        current
            DESCRIPTION
                "This table specifies the extend information for configuring and
                 status monitoring that are common to all service types
                 and PSN types.
                 The index of this entry is pwIndex.
                "
            INDEX  { pwIndex }
            ::= { hwPwExtTable 1 }
        
        HwPwExtEntry ::=
            SEQUENCE {
                hwPwPriority
                    INTEGER,
                hwPwPrimaryPwIndex
                    Unsigned32,
                hwPwVCCVCapabilities
                    BITS,
                hwPwVCCVStatus
                    BITS,
                hwPwFlowLabel
                    BITS,
                hwPwAtmCfgTimeout
                    Unsigned32,
                hwPwPriMappingProfName
                    OCTET STRING,
                hwPwFlowLabelCapabilities
                    BITS,
                hwPwFlowlabelStatus
                    BITS,
                hwPwStatisticSwitch
                    INTEGER,
                hwPwTnlPolicy  
                    OCTET STRING,
                hwPwPayloadType
                    Integer32,
                hwPwSnStartNum
                    Integer32,
                hwPwRcvSsrcId
                    Unsigned32,
                hwPwTxSsrcId
                    Unsigned32
             }

        hwPwPriority OBJECT-TYPE
            SYNTAX INTEGER
                {
                    primaryPW(1),
                    secondaryPW(2)
                }
            MAX-ACCESS    read-write
            STATUS        current
            DESCRIPTION
                "This value indicate Primary PW or Secondary PW.
                 Options: 
                 1. primaryPW(1)   -indicates the primary member of the PW protect group
                 2. secondaryPW(2) -indicates the secondary member of the PW protect group
                " 
            ::= { hwPwExtEntry 1 }

        hwPwPrimaryPwIndex OBJECT-TYPE
            SYNTAX        Unsigned32
            MAX-ACCESS    read-write
            STATUS        current
            DESCRIPTION
                "The value that represents the corresponding primary PW in the pwTable.
                " 
            ::= { hwPwExtEntry 2 }

        hwPwVCCVCapabilities OBJECT-TYPE
            SYNTAX BITS
                {
                ccCw(0),
                ccAlert(1),
                ccTTL(2),
                cvIcmpping(3),
                cvLspping(4),
                cvBfd(5)
                }            
            MAX-ACCESS read-write
            STATUS current
            DESCRIPTION
                "Config the optional VCCV capabilities of the PW.
                "
            ::= { hwPwExtEntry 3 }

        hwPwVCCVStatus OBJECT-TYPE
            SYNTAX BITS
                {
                ccCw(0),
                ccAlert(1),
                ccTTL(2),
                cvIcmpping(3),
                cvLspping(4),
                cvBfd(5)
                }            
            MAX-ACCESS read-only
            STATUS current
            DESCRIPTION
                "Indicates the optional VCCV capabilities of the PW.
                "
            ::= { hwPwExtEntry 4 }

        hwPwFlowLabel OBJECT-TYPE
            SYNTAX BITS
                {
                    sip(0),
                    dip(1),
                    smac(2),
                    dmac(3)
                }
            MAX-ACCESS read-write
            STATUS current
            DESCRIPTION
                "Indicates the optional flow label capabilities of the PW.
                " 
            ::= { hwPwExtEntry 5 }

         hwPwAtmCfgTimeout OBJECT-TYPE
         	SYNTAX        Unsigned32 (0..50)
         	MAX-ACCESS    read-write
         	STATUS current
         	DESCRIPTION
         	    "Indicates max ATM cells encapsulation delay time. 
         	     Range: 0-50 
         	     Default: 0
         	     Unit: millisecond
         	    "
            ::= { hwPwExtEntry 6 }

         hwPwPriMappingProfName OBJECT-TYPE
         	SYNTAX        OCTET STRING (SIZE (1..32))
         	MAX-ACCESS    read-write
         	STATUS current
         	DESCRIPTION
         	    "QoS priority mapping profile name for PW, a string of 1-32 characters. 
 	             There are all together 92 valid characters for the name. 
 	             These characters include the following: 
 	             uppercase and lowercase English letters (52 characters), numerals (0-9), 
 	             and 30 symbols: ! # $ % & ' ( ) * + , - . / : ; < = > @ [ \ ] ^ _ `  |  ~~.
         	    "
            ::= { hwPwExtEntry 7 }
        
        hwPwFlowLabelCapabilities OBJECT-TYPE
            SYNTAX BITS
                {
                    receive(0),
                    transmit(1)
                }
            MAX-ACCESS read-write
            STATUS current
            DESCRIPTION
                "Indicates the PW flow label capability.
                " 
            ::= { hwPwExtEntry 8 }
            
        hwPwFlowlabelStatus OBJECT-TYPE
            SYNTAX BITS
                {
                    receive(0),
                    transmit(1)
                }
            MAX-ACCESS read-only
            STATUS current
            DESCRIPTION
                "Indicates the negotiation result of the PW flow label capability.
                 The negotiation result of static PW is consistent with local configuration.
                " 
            ::= { hwPwExtEntry 9 }

        hwPwStatisticSwitch OBJECT-TYPE
            SYNTAX 	INTEGER
                	{
                    	enable(1),
                    	disable(2)
                	}
            MAX-ACCESS read-write
            STATUS current
            DESCRIPTION
                "Used to enable or disable the traffic statistic function of pw.
			 	 Options:
			 	 1. enable(1)  -indicates that the traffic statistic function is enabled
			 	 2. disable(2) -indicates that the traffic statistic function is disabled
			 	 Default: disable(2)
                " 
            ::= { hwPwExtEntry 10 }
 
          hwPwTnlPolicy OBJECT-TYPE
         	SYNTAX        OCTET STRING (SIZE (0..39))
         	MAX-ACCESS    read-write
         	STATUS current
         	DESCRIPTION
         	    "
         	    Used to configure the tunnel policy used by the PW.
         	    "
            ::= { hwPwExtEntry 11 }

         hwPwPayloadType OBJECT-TYPE
           SYNTAX Integer32 (0..127)
           MAX-ACCESS read-write
           STATUS current
           DESCRIPTION
               "The payload type in RTP header.
               Range: 0-127
               Default: 0
               "
           DEFVAL { 0 }
           ::= { hwPwExtEntry 12 }
     
         hwPwSnStartNum OBJECT-TYPE
           SYNTAX Integer32 (0..1)
           MAX-ACCESS read-write
           STATUS current
           DESCRIPTION
               "The sn start number in RTP header.
               Range: 0-1
               Default: 0
               "
           DEFVAL { 0 }
           ::= { hwPwExtEntry 13 }

         hwPwRcvSsrcId OBJECT-TYPE
           SYNTAX Unsigned32
           MAX-ACCESS read-write
           STATUS current
           DESCRIPTION
               "The recieve SSRC ID in RTP header.
               Default: 0
               "
           DEFVAL { 0 }
           ::= { hwPwExtEntry 14 }

         hwPwTxSsrcId OBJECT-TYPE
           SYNTAX Unsigned32
           MAX-ACCESS read-write
           STATUS current
           DESCRIPTION
               "The transmit SSRC ID in RTP header.
               Default: 0
               "
           DEFVAL { 0 }
           ::= { hwPwExtEntry 15 }
 
        hwPwCmdTdmDefectStatsTable OBJECT-TYPE
            SYNTAX SEQUENCE OF HwPwCmdTdmDefectStatsEntry
            MAX-ACCESS not-accessible
            STATUS current
            DESCRIPTION
                "This table is a read-only table. The purpose of 
                 this table is to keep statistical information about
                 the TDM failure alarm. The index of this table is pwIndex.
                "
            ::= { hwPwCmdObjects 27 }

        hwPwCmdTdmDefectStatsEntry OBJECT-TYPE
            SYNTAX HwPwCmdTdmDefectStatsEntry
            MAX-ACCESS not-accessible
            STATUS current
            DESCRIPTION
                "This table is a read-only table. The purpose of 
                 this table is to keep statistical information about
                 the TDM failure alarm.
                 The index of this entry is pwIndex.
                "
            INDEX { pwIndex }
            ::= { hwPwCmdTdmDefectStatsTable 1 }
        
        HwPwCmdTdmDefectStatsEntry ::=
            SEQUENCE {
                hwPwCmdTdmDefectStatsJtrBfrOverRun
                    Counter32,
                hwPwCmdTdmDefectStatsJtrBfrOverRunClear
                    Counter32,
                hwPwCmdTdmDefectStatsJtrBfrUnderRun
                    Counter32,
                hwPwCmdTdmDefectStatsJtrBfrUnderRunClear
                    Counter32,
                hwPwCmdTdmDefectStatsR1
                    Counter32,
                hwPwCmdTdmDefectStatsR1Clear
                    Counter32,
                hwPwCmdTdmDefectStatsLM010
                    Counter32,
                hwPwCmdTdmDefectStatsLM010Clear
                    Counter32,
                hwPwCmdTdmDefectStatsLM100
                    Counter32,
                hwPwCmdTdmDefectStatsLM100Clear
                    Counter32
             }
            
        hwPwCmdTdmDefectStatsJtrBfrOverRun OBJECT-TYPE
            SYNTAX Counter32
            MAX-ACCESS read-only
            STATUS current
            DESCRIPTION
                "Indicates the number of times that the 
                 jitter buffer overrun.
                "
            ::= { hwPwCmdTdmDefectStatsEntry 1 }
        
        hwPwCmdTdmDefectStatsJtrBfrOverRunClear OBJECT-TYPE
            SYNTAX Counter32
            MAX-ACCESS read-only
            STATUS current
            DESCRIPTION
                "Indicates the number of times that the system
                 is restored from overrun of the jitter buffer.
                "
            ::= { hwPwCmdTdmDefectStatsEntry 2 }

        hwPwCmdTdmDefectStatsJtrBfrUnderRun OBJECT-TYPE
            SYNTAX Counter32
            MAX-ACCESS read-only
            STATUS current
            DESCRIPTION
                "Indicates the number of times that the 
                 jitter buffer overrun.
                "
            ::= { hwPwCmdTdmDefectStatsEntry 3 }

        hwPwCmdTdmDefectStatsJtrBfrUnderRunClear OBJECT-TYPE
            SYNTAX Counter32
            MAX-ACCESS read-only
            STATUS current
            DESCRIPTION
                "Indicates the number of times that the system
                 is restored from underrun of the jitter buffer.
                "
            ::= { hwPwCmdTdmDefectStatsEntry 4 }
        
        hwPwCmdTdmDefectStatsR1 OBJECT-TYPE
            SYNTAX Counter32
            MAX-ACCESS read-only
            STATUS current
            DESCRIPTION
                "Indicates the number of times that the PSN side receives 
                 an alarm triggered by R = 1. When the peer end didn't 
                 receive for failure. For example, jitter buffer underrun,
                 Then the local end receives an packet with R = 1.
                "
            ::= { hwPwCmdTdmDefectStatsEntry 5 }

        hwPwCmdTdmDefectStatsR1Clear OBJECT-TYPE
            SYNTAX Counter32
            MAX-ACCESS read-only
            STATUS current
            DESCRIPTION
                "Indicates the number of times that the system is restored
                 from R1.
                "
            ::= { hwPwCmdTdmDefectStatsEntry 6 }

        hwPwCmdTdmDefectStatsLM010 OBJECT-TYPE
            SYNTAX Counter32
            MAX-ACCESS read-only
            STATUS current
            DESCRIPTION
                "Indicates the number of times that the PSN side receives 
                 an alarm triggered by M = 1. Only for the CESOPSN, When 
                 the local end receives a RDI alarm from the AC side, 
                 the local end sets the control flag M to 1. Then, the 
                 peer end receives an LM(010) packet.
                "
            ::= { hwPwCmdTdmDefectStatsEntry 7 }
        
        hwPwCmdTdmDefectStatsLM010Clear OBJECT-TYPE
            SYNTAX Counter32
            MAX-ACCESS read-only
            STATUS current
            DESCRIPTION
                "Indicates the number of times that the system is restored 
                 from LM(010) to LM(000).
                "
            ::= { hwPwCmdTdmDefectStatsEntry 8 }

        hwPwCmdTdmDefectStatsLM100 OBJECT-TYPE
            SYNTAX Counter32
            MAX-ACCESS read-only
            STATUS current
            DESCRIPTION
                "Indicates the number of times that the PSN side receives 
                 an alarm triggered by L = 1. When the local end receives 
                 a LOS, LOF, AIS, or LMFA alarm from the AC side, 
                 the local end sets the control flag L to 1. 
                 Then, the peer end receives an LM(100) packet.
                "
            ::= { hwPwCmdTdmDefectStatsEntry 9 }

        hwPwCmdTdmDefectStatsLM100Clear OBJECT-TYPE
            SYNTAX Counter32
            MAX-ACCESS read-only
            STATUS current
            DESCRIPTION
                "Indicates the number of times that the system is restored 
                 from LM(100) to LM(000).
                "
            ::= { hwPwCmdTdmDefectStatsEntry 10 }

        hwPwPriMappingTable OBJECT-TYPE
            SYNTAX SEQUENCE OF HwPwPriMappingEntry
            MAX-ACCESS not-accessible
            STATUS current
            DESCRIPTION
                "MPLS priority mapping profile table for PW.
                 The purpose of this table is to set and query MPLS priority mapping profile.
                 The index of this table is hwPwPriMappingProfileName.
                "
            ::= { hwPwCmdObjects 28 }

        hwPwPriMappingEntry OBJECT-TYPE
            SYNTAX HwPwPriMappingEntry
            MAX-ACCESS not-accessible
            STATUS current
            DESCRIPTION
                "MPLS priority mapping profile table for PW.
                 The purpose of this table is to set and query MPLS priority mapping profile.
                 The index of this entry is hwPwPriMappingProfileName.
                "
            INDEX { hwPwPriMappingProfileName }
            ::= { hwPwPriMappingTable 1 }
        
        HwPwPriMappingEntry ::=
            SEQUENCE {
                hwPwPriMappingProfileName
                    OCTET STRING,
                hwPwInboundInputPriList
                    OCTET STRING,
                hwPwInboundOutputPriList
                    OCTET STRING,
                hwPwOutboundInputPriList
                    OCTET STRING,
                hwPwOutboundOutputPriList
                    OCTET STRING,
                hwPwPriMappingProfileRowStatus
                    RowStatus
             }
            
        hwPwPriMappingProfileName OBJECT-TYPE
            SYNTAX OCTET STRING (SIZE (1..32))
            MAX-ACCESS not-accessible
            STATUS current
            DESCRIPTION
                "QoS priority mapping profile name for PW, a string of 1-32 characters. 
 	             There are all together 92 valid characters for the name. 
 	             These characters include the following: 
 	             uppercase and lowercase English letters (52 characters), numerals (0-9), 
 	             and 30 symbols: ! # $ % & ' ( ) * + , - . / : ; < = > @ [ \ ] ^ _ `  |  ~~.
         	    "
            ::= { hwPwPriMappingEntry 1 }
        
        hwPwInboundInputPriList OBJECT-TYPE
            SYNTAX OCTET STRING (SIZE (1..15))
            MAX-ACCESS read-write
            STATUS current
            DESCRIPTION
                "Inbound input priority list(MPLS PW label EXP) of QoS priority mapping.
                 Legal character include: 0-7,hyphen,comma.
                 Example legal string: 0,2,4-7.
                "
            ::= { hwPwPriMappingEntry 2 }

        hwPwInboundOutputPriList OBJECT-TYPE
            SYNTAX OCTET STRING (SIZE (1..15))
            MAX-ACCESS read-write
            STATUS current
            DESCRIPTION
                "Inbound output priority list(ethernet VLAN tag 802.1p) of QoS priority mapping.
                 Legal character include: 0-7,hyphen,comma.
                 Example legal string: 0,2,4-7.                
                "
            ::= { hwPwPriMappingEntry 3 }

        hwPwOutboundInputPriList OBJECT-TYPE
            SYNTAX OCTET STRING (SIZE (1..15))
            MAX-ACCESS read-write
            STATUS current
            DESCRIPTION
                "Outbound input priority list(ethernet VLAN tag 802.1p) of QoS priority mapping.
                 Legal character include: 0-7,hyphen,comma.
                 Example legal string: 0,2,4-7.                
                "
            ::= { hwPwPriMappingEntry 4 }

        hwPwOutboundOutputPriList OBJECT-TYPE
            SYNTAX OCTET STRING (SIZE (1..15))
            MAX-ACCESS read-write
            STATUS current
            DESCRIPTION
                "Outbound output priority list(MPLS PW label EXP) of QoS priority mapping.
                 Legal character include: 0-7,hyphen,comma.
                 Example legal string: 0,2,4-7.                
                "
            ::= { hwPwPriMappingEntry 5 }   

        hwPwPriMappingProfileRowStatus OBJECT-TYPE
            SYNTAX RowStatus (1..6)
            MAX-ACCESS read-create
            STATUS current
            DESCRIPTION
                "For creating and modifying this row. None of the 
                 read-create objects in the conceptual rows may be changed  
                 when this object is in the active(1) state.
                 Options:
                 1. active(1)      -indicates query operation
                 2. createAndGo(4) -indicates creating committed
                 3. destroy(6)     -indicates deleting committed
                "
            ::= { hwPwPriMappingEntry 6 }

--
-- hwPwCmdStatisticTable
--
        hwPwCmdStatisticTable OBJECT-TYPE
            SYNTAX SEQUENCE OF HwPwCmdStatisticEntry
            MAX-ACCESS not-accessible
            STATUS current
            DESCRIPTION
                "This table is used to query or clear the 
                 traffic statistic info of PW.
                 The index of this table is pwIndex.
                "
            ::= { hwPwCmdObjects 29 }

        hwPwCmdStatisticEntry OBJECT-TYPE
            SYNTAX HwPwCmdStatisticEntry
            MAX-ACCESS not-accessible
            STATUS current
            DESCRIPTION
                "This table is used to query or clear the 
                 traffic statistic info of PW.
                 The index of this entry is pwIndex.
                "
            INDEX { pwIndex }
            ::= { hwPwCmdStatisticTable 1 }

        HwPwCmdStatisticEntry ::= SEQUENCE 
        {
           	hwPwCmdStatisticUpstreamOctectsP0		Counter64,
           	hwPwCmdStatisticUpstreamPacketsP0		Counter32,
           	hwPwCmdStatisticUpstreamOctectsP1		Counter64,
           	hwPwCmdStatisticUpstreamPacketsP1		Counter32,
           	hwPwCmdStatisticUpstreamOctectsP2		Counter64,
           	hwPwCmdStatisticUpstreamPacketsP2		Counter32,
           	hwPwCmdStatisticUpstreamOctectsP3		Counter64,
           	hwPwCmdStatisticUpstreamPacketsP3		Counter32,
           	hwPwCmdStatisticUpstreamOctectsP4		Counter64,
           	hwPwCmdStatisticUpstreamPacketsP4		Counter32,
           	hwPwCmdStatisticUpstreamOctectsP5		Counter64,
           	hwPwCmdStatisticUpstreamPacketsP5		Counter32,
           	hwPwCmdStatisticUpstreamOctectsP6		Counter64,
           	hwPwCmdStatisticUpstreamPacketsP6		Counter32,
           	hwPwCmdStatisticUpstreamOctectsP7		Counter64,
           	hwPwCmdStatisticUpstreamPacketsP7		Counter32,
           	hwPwCmdStatisticDownstreamOctectsP0		Counter64,
           	hwPwCmdStatisticDownstreamPacketsP0		Counter32,
           	hwPwCmdStatisticDownstreamOctectsP1		Counter64,
           	hwPwCmdStatisticDownstreamPacketsP1		Counter32,
           	hwPwCmdStatisticDownstreamOctectsP2		Counter64,
           	hwPwCmdStatisticDownstreamPacketsP2		Counter32,
           	hwPwCmdStatisticDownstreamOctectsP3		Counter64,
           	hwPwCmdStatisticDownstreamPacketsP3		Counter32,
           	hwPwCmdStatisticDownstreamOctectsP4		Counter64,
           	hwPwCmdStatisticDownstreamPacketsP4		Counter32,
           	hwPwCmdStatisticDownstreamOctectsP5		Counter64,
           	hwPwCmdStatisticDownstreamPacketsP5		Counter32,
           	hwPwCmdStatisticDownstreamOctectsP6		Counter64,
           	hwPwCmdStatisticDownstreamPacketsP6		Counter32,
           	hwPwCmdStatisticDownstreamOctectsP7		Counter64,
           	hwPwCmdStatisticDownstreamPacketsP7		Counter32,
           	hwPwCmdStatisticClear				INTEGER
        }


        hwPwCmdStatisticUpstreamOctectsP0 OBJECT-TYPE
            SYNTAX          Counter64
            MAX-ACCESS      read-only
            STATUS          current
            DESCRIPTION
                "The total number of upstream octets with priority equel to 0.
                "
            ::= { hwPwCmdStatisticEntry 1 }

        hwPwCmdStatisticUpstreamPacketsP0 OBJECT-TYPE
            SYNTAX          Counter32
            MAX-ACCESS      read-only
            STATUS          current
            DESCRIPTION
                "The total number of upstream packets with priority equel to 0.
                "
            ::= { hwPwCmdStatisticEntry 2 }

        hwPwCmdStatisticUpstreamOctectsP1 OBJECT-TYPE
            SYNTAX          Counter64
            MAX-ACCESS      read-only
            STATUS          current
            DESCRIPTION
                "The total number of upstream octets with priority equel to 1.
                "
            ::= { hwPwCmdStatisticEntry 3 }

        hwPwCmdStatisticUpstreamPacketsP1 OBJECT-TYPE
            SYNTAX          Counter32
            MAX-ACCESS      read-only
            STATUS          current
            DESCRIPTION
                "The total number of upstream packets with priority equel to 1.
                "
            ::= { hwPwCmdStatisticEntry 4 }

        hwPwCmdStatisticUpstreamOctectsP2 OBJECT-TYPE
            SYNTAX          Counter64
            MAX-ACCESS      read-only
            STATUS          current
            DESCRIPTION
                "The total number of upstream octets with priority equel to 2.
                "
            ::= { hwPwCmdStatisticEntry 5 }

        hwPwCmdStatisticUpstreamPacketsP2 OBJECT-TYPE
            SYNTAX          Counter32
            MAX-ACCESS      read-only
            STATUS          current
            DESCRIPTION
                "The total number of upstream packets with priority equel to 2.
                "
            ::= { hwPwCmdStatisticEntry 6 }

        hwPwCmdStatisticUpstreamOctectsP3 OBJECT-TYPE
            SYNTAX          Counter64
            MAX-ACCESS      read-only
            STATUS          current
            DESCRIPTION
                "The total number of upstream octets with priority equel to 3.
                "
            ::= { hwPwCmdStatisticEntry 7 }

        hwPwCmdStatisticUpstreamPacketsP3 OBJECT-TYPE
            SYNTAX          Counter32
            MAX-ACCESS      read-only
            STATUS          current
            DESCRIPTION
                "The total number of upstream packets with priority equel to 3.
                "
            ::= { hwPwCmdStatisticEntry 8 }

        hwPwCmdStatisticUpstreamOctectsP4 OBJECT-TYPE
            SYNTAX          Counter64
            MAX-ACCESS      read-only
            STATUS          current
            DESCRIPTION
                "The total number of upstream octets with priority equel to 4.
                "
            ::= { hwPwCmdStatisticEntry 9 }

        hwPwCmdStatisticUpstreamPacketsP4 OBJECT-TYPE
            SYNTAX          Counter32
            MAX-ACCESS      read-only
            STATUS          current
            DESCRIPTION
                "The total number of upstream packets with priority equel to 4.
                "
            ::= { hwPwCmdStatisticEntry 10 }

        hwPwCmdStatisticUpstreamOctectsP5 OBJECT-TYPE
            SYNTAX          Counter64
            MAX-ACCESS      read-only
            STATUS          current
            DESCRIPTION
                "The total number of upstream octets with priority equel to 5.
                "
            ::= { hwPwCmdStatisticEntry 11 }

        hwPwCmdStatisticUpstreamPacketsP5 OBJECT-TYPE
            SYNTAX          Counter32
            MAX-ACCESS      read-only
            STATUS          current
            DESCRIPTION
                "The total number of upstream packets with priority equel to 5.
                "
            ::= { hwPwCmdStatisticEntry 12 }

        hwPwCmdStatisticUpstreamOctectsP6 OBJECT-TYPE
            SYNTAX          Counter64
            MAX-ACCESS      read-only
            STATUS          current
            DESCRIPTION
                "The total number of upstream octets with priority equel to 6.
                "
            ::= { hwPwCmdStatisticEntry 13 }

        hwPwCmdStatisticUpstreamPacketsP6 OBJECT-TYPE
            SYNTAX          Counter32
            MAX-ACCESS      read-only
            STATUS          current
            DESCRIPTION
                "The total number of upstream packets with priority equel to 6.
                "
            ::= { hwPwCmdStatisticEntry 14 }

        hwPwCmdStatisticUpstreamOctectsP7 OBJECT-TYPE
            SYNTAX          Counter64
            MAX-ACCESS      read-only
            STATUS          current
            DESCRIPTION
                "The total number of upstream octets with priority equel to 7.
                "
            ::= { hwPwCmdStatisticEntry 15 }

        hwPwCmdStatisticUpstreamPacketsP7 OBJECT-TYPE
            SYNTAX          Counter32
            MAX-ACCESS      read-only
            STATUS          current
            DESCRIPTION
                "The total number of upstream packets with priority equel to 7.
                "
            ::= { hwPwCmdStatisticEntry 16 }

        hwPwCmdStatisticDownstreamOctectsP0 OBJECT-TYPE
            SYNTAX          Counter64
            MAX-ACCESS      read-only
            STATUS          current
            DESCRIPTION
                "The total number of downstream octets with priority equel to 0.
                "
            ::= { hwPwCmdStatisticEntry 17 }

        hwPwCmdStatisticDownstreamPacketsP0 OBJECT-TYPE
            SYNTAX          Counter32
            MAX-ACCESS      read-only
            STATUS          current
            DESCRIPTION
                "The total number of downstream packets with priority equel to 0.
                "
            ::= { hwPwCmdStatisticEntry 18 }

        hwPwCmdStatisticDownstreamOctectsP1 OBJECT-TYPE
            SYNTAX          Counter64
            MAX-ACCESS      read-only
            STATUS          current
            DESCRIPTION
                "The total number of downstream octets with priority equel to 1.
                "
            ::= { hwPwCmdStatisticEntry 19 }

        hwPwCmdStatisticDownstreamPacketsP1 OBJECT-TYPE
            SYNTAX          Counter32
            MAX-ACCESS      read-only
            STATUS          current
            DESCRIPTION
                "The total number of downstream packets with priority equel to 1.
                "
            ::= { hwPwCmdStatisticEntry 20 }

        hwPwCmdStatisticDownstreamOctectsP2 OBJECT-TYPE
            SYNTAX          Counter64
            MAX-ACCESS      read-only
            STATUS          current
            DESCRIPTION
                "The total number of downstream octets with priority equel to 2.
                "
            ::= { hwPwCmdStatisticEntry 21 }

        hwPwCmdStatisticDownstreamPacketsP2 OBJECT-TYPE
            SYNTAX          Counter32
            MAX-ACCESS      read-only
            STATUS          current
            DESCRIPTION
                "The total number of downstream packets with priority equel to 2.
                "
            ::= { hwPwCmdStatisticEntry 22 }

        hwPwCmdStatisticDownstreamOctectsP3 OBJECT-TYPE
            SYNTAX          Counter64
            MAX-ACCESS      read-only
            STATUS          current
            DESCRIPTION
                "The total number of downstream octets with priority equel to 3.
                "
            ::= { hwPwCmdStatisticEntry 23 }

        hwPwCmdStatisticDownstreamPacketsP3 OBJECT-TYPE
            SYNTAX          Counter32
            MAX-ACCESS      read-only
            STATUS          current
            DESCRIPTION
                "The total number of downstream packets with priority equel to 3.
                "
            ::= { hwPwCmdStatisticEntry 24 }

        hwPwCmdStatisticDownstreamOctectsP4 OBJECT-TYPE
            SYNTAX          Counter64
            MAX-ACCESS      read-only
            STATUS          current
            DESCRIPTION
                "The total number of downstream octets with priority equel to 4.
                "
            ::= { hwPwCmdStatisticEntry 25 }

        hwPwCmdStatisticDownstreamPacketsP4 OBJECT-TYPE
            SYNTAX          Counter32
            MAX-ACCESS      read-only
            STATUS          current
            DESCRIPTION
                "The total number of downstream packets with priority equel to 4.
                "
            ::= { hwPwCmdStatisticEntry 26 }

        hwPwCmdStatisticDownstreamOctectsP5 OBJECT-TYPE
            SYNTAX          Counter64
            MAX-ACCESS      read-only
            STATUS          current
            DESCRIPTION
                "The total number of downstream octets with priority equel to 5.
                "
            ::= { hwPwCmdStatisticEntry 27 }

        hwPwCmdStatisticDownstreamPacketsP5 OBJECT-TYPE
            SYNTAX          Counter32
            MAX-ACCESS      read-only
            STATUS          current
            DESCRIPTION
                "The total number of downstream packets with priority equel to 5.
                "
            ::= { hwPwCmdStatisticEntry 28 }

        hwPwCmdStatisticDownstreamOctectsP6 OBJECT-TYPE
            SYNTAX          Counter64
            MAX-ACCESS      read-only
            STATUS          current
            DESCRIPTION
                "The total number of downstream octets with priority equel to 6.
                "
            ::= { hwPwCmdStatisticEntry 29 }

        hwPwCmdStatisticDownstreamPacketsP6 OBJECT-TYPE
            SYNTAX          Counter32
            MAX-ACCESS      read-only
            STATUS          current
            DESCRIPTION
                "The total number of downstream packets with priority equel to 6.
                "
            ::= { hwPwCmdStatisticEntry 30 }

        hwPwCmdStatisticDownstreamOctectsP7 OBJECT-TYPE
            SYNTAX          Counter64
            MAX-ACCESS      read-only
            STATUS          current
            DESCRIPTION
                "The total number of downstream octets with priority equel to 7.
                "
            ::= { hwPwCmdStatisticEntry 31 }

        hwPwCmdStatisticDownstreamPacketsP7 OBJECT-TYPE
            SYNTAX          Counter32
            MAX-ACCESS      read-only
            STATUS          current
            DESCRIPTION
                "The total number of downstream packets with priority equel to 7.
                "
            ::= { hwPwCmdStatisticEntry 32 }

        hwPwCmdStatisticClear OBJECT-TYPE
       		SYNTAX     INTEGER{ clear(1) }
       		MAX-ACCESS read-write
       		STATUS     current
       		DESCRIPTION
             	"Clear the traffic statistics of this pw.
              	 Options:
              	 1. clear(1) -clear the traffic statistics of this pw
             	"
            ::= { hwPwCmdStatisticEntry 33 }

        hwPwStatisticClearAll OBJECT-TYPE
       		SYNTAX     INTEGER{ clear(1) }
       		MAX-ACCESS read-write
       		STATUS     current
       		DESCRIPTION
             	"Clear the traffic statistics of all PWs.
              	 Options:
              	 1. clear(1) -clear the traffic statistics of all PWs
             	"
            ::= { hwPwCmdObjects 30 }             
--
-- hwPwRedundancyTable
--
       hwPwRedundancyTable OBJECT-TYPE
            SYNTAX SEQUENCE OF HwPwRedundancyEntry
            MAX-ACCESS not-accessible
            STATUS current
            DESCRIPTION
                "This table specifies information for pw redundancy.
                 The index of this table is pwIndex.
                "
            ::= { hwPwCmdObjects 31 }
        
        hwPwRedundancyEntry OBJECT-TYPE
            SYNTAX HwPwRedundancyEntry
            MAX-ACCESS not-accessible
            STATUS current
            DESCRIPTION
                "This table specifies information for pw redundancy.
                 The index of this entry is pwIndex.
                "
            INDEX { pwIndex }
            ::= { hwPwRedundancyTable 1 }
        
        HwPwRedundancyEntry ::=
            SEQUENCE { 
                hwPwRedundancyMode
                    INTEGER,
                hwPwStreamDualReceiving
                    INTEGER
             }
        
        hwPwRedundancyMode OBJECT-TYPE
            SYNTAX INTEGER
                {
                    master(1),
                    independent(2)
                }          
            MAX-ACCESS read-create
            STATUS current
            DESCRIPTION
                "Indicates the mode of the pw redundancy.
                 Options:
                 1. master(1)      -indicates that the pw redundancy mode is master
                 2. independent(2) -indicates that the pw redundancy mode is independent
                 Default: master(1)
                "
            ::= { hwPwRedundancyEntry 1 }

        hwPwStreamDualReceiving OBJECT-TYPE
            SYNTAX INTEGER
                {
                    enable(1),
                    disable(2)
                }          
            MAX-ACCESS read-create
            STATUS current
            DESCRIPTION
                "Indicates the stream receiving mode of the pw redundancy.
                 Options:
                 1. enable(1)   -indicates that the stream receiving mode of the pw redundancy is dual
                 2. disable(2)  -indicates that the stream receiving mode of the pw redundancy is single
                 Default: disable(2)
                "
            ::= { hwPwRedundancyEntry 2 }
 
         hwPwCmdPwCarExtTable OBJECT-TYPE
            SYNTAX SEQUENCE OF HwPwCmdPwCarExtEntry
            MAX-ACCESS not-accessible
            STATUS current
            DESCRIPTION
                "This table specifies information for PW CAR.
                 The index of this table is pwIndex.
                "
            ::= { hwPwCmdObjects 32 }
            
        hwPwCmdPwCarExtEntry OBJECT-TYPE
            SYNTAX HwPwCmdPwCarExtEntry
            MAX-ACCESS not-accessible
            STATUS current
            DESCRIPTION
                "This table specifies information for PW CAR.
                 The index of this entry is pwIndex.
                "
            INDEX { pwIndex }
            ::= { hwPwCmdPwCarExtTable 1 }
            
        HwPwCmdPwCarExtEntry ::=
            SEQUENCE { 
                hwPwCmdPwCarExtCir
                    Unsigned32,
                hwPwCmdPwCarExtCbs
                    Unsigned32,
                hwPwCmdPwCarExtPir
                    Unsigned32,
                hwPwCmdPwCarExtPbs
                    Unsigned32,                       
                hwPwCmdPwCarExtRowStatus
                    RowStatus    
             }        
                            
        hwPwCmdPwCarExtCir OBJECT-TYPE
            SYNTAX Unsigned32 (1..1048575)
            MAX-ACCESS read-write
            STATUS current
            DESCRIPTION
                "Committed information rate, it is the necessary parameter for adding pw car.
                 Range: 1-1048575 
                 Unit: 64Kbit/s
                "
            ::= { hwPwCmdPwCarExtEntry 1 }  
                            
        hwPwCmdPwCarExtCbs OBJECT-TYPE
            SYNTAX Unsigned32 (1..32767)
            MAX-ACCESS read-write
            STATUS current
            DESCRIPTION
                "Committed burst size, default value is ((cir+8191)/8192+1).
                 Range: 1-32767 
                 Unit: 2KByte/s
                "
            ::= { hwPwCmdPwCarExtEntry 2 } 
            
        hwPwCmdPwCarExtPir OBJECT-TYPE
            SYNTAX Unsigned32 (1..1048575)
            MAX-ACCESS read-write
            STATUS current
            DESCRIPTION
                "Peak information rate, default value is double of committed information rate.
                 Range: 1-1048575 
                 Unit: 64Kbit/s
                "
            ::= { hwPwCmdPwCarExtEntry 3 }  
                            
        hwPwCmdPwCarExtPbs OBJECT-TYPE
            SYNTAX Unsigned32 (1..32767)
            MAX-ACCESS read-write
            STATUS current
            DESCRIPTION
                "Peak burst size, default value is MAX(((pir+8191)/8192 + 1), cbs).
                 Range: 1-32767 
                 Unit: 2KByte/s
                "
            ::= { hwPwCmdPwCarExtEntry 4 }  

        hwPwCmdPwCarExtRowStatus OBJECT-TYPE
            SYNTAX RowStatus
            MAX-ACCESS read-create
            STATUS current
            DESCRIPTION
                "For creating and modifying this row. None of the 
                 read-create objects in the conceptual rows may be changed  
                 when this object is in the active(1) state.
                 Options:
                 1. active(1)      -indicates query operation
                 2. createAndGo(4) -indicates creating committed access rate parameters of a PW
                 3. destroy(6)     -indicates deleting committed access rate parameters of a PW
                "
            ::= { hwPwCmdPwCarExtEntry 5 }     
 
 
--
-- PW VCCV table
--

        hwPwAutoVccvTable OBJECT-TYPE
            SYNTAX SEQUENCE OF HwPwAutoVccvEntry
            MAX-ACCESS not-accessible
            STATUS current
            DESCRIPTION
                "This table specifies information for PW VCCV ping.
                 The index of this table is pwIndex.
                "
            ::= { hwPwCmdObjects 33 }
        
        hwPwAutoVccvEntry OBJECT-TYPE
            SYNTAX HwPwAutoVccvEntry
            MAX-ACCESS not-accessible
            STATUS current
            DESCRIPTION
                "This table specifies information for PW VCCV ping.
                 The index of this entry is pwIndex.
                "
            INDEX { pwIndex }
            ::= { hwPwAutoVccvTable 1 }
        
        HwPwAutoVccvEntry ::=
            SEQUENCE { 
                hwPwAutoVccvReplyMode
                    INTEGER,
                hwPwAutoVccvFrequency
                    INTEGER,
                hwPwAutoVccvTimeoutLimit
                    Unsigned32,
                hwPwAutoVccvRecoverLimit
                    Unsigned32,
                hwPwAutoVccvRemotePwID
                    Unsigned32,
                hwPwAutoVccvRemoteIpAddress
                    IpAddress,
                hwPwAutoVccvTtl
                    Unsigned32,
                hwPwAutoVccvPingStatus
                    INTEGER,
                hwPwAutoVccvPingSuccessNum
                    Unsigned32,
                hwPwAutoVccvPingTimeOutNum
                    Unsigned32,
                hwPwAutoVccvStatisticsReset
                    INTEGER,
                hwPwAutoVccvPipeUniform
                    INTEGER,
                hwPwAutoVccvRowStatus
                    RowStatus
             }               
        
        hwPwAutoVccvReplyMode OBJECT-TYPE
            SYNTAX INTEGER
                {
                    doNotReply(1),
                    replyViaAnIPv4IPv6UdpPacket(2),
                    replyViaAnIPv4IPv6UdpPacketWithRouterAlert(3),
                    replyViaApplicationLevelControlChannel(4)
                }
            MAX-ACCESS read-write
            STATUS current
            DESCRIPTION
                "The reply mode for the VCCV packet.
                 Options:
                 1. doNotReply(1)                                 -indicates that there is no reply for VCCV PING
                 2. replyViaAnIPv4IPv6UdpPacket(2)                -indicates that reply for VCCV PING using IP UDP packets
                 3. replyViaAnIPv4IPv6UdpPacketWithRouterAlert(3) -indicates that reply for VCCV PING using IP UDP packets with router alert
                 4. replyViaApplicationLevelControlChannel(4)     -indicates that reply for VCCV PING using control channel
                "  
            DEFVAL { replyViaApplicationLevelControlChannel }
            ::= { hwPwAutoVccvEntry 1 }
                
        hwPwAutoVccvFrequency OBJECT-TYPE
            SYNTAX INTEGER
                {
                    freq1000ms(1000),
                    freq2000ms(2000),
                    freq5000ms(5000),
                    freq10000ms(10000)
                }
            MAX-ACCESS read-write
            STATUS current
            DESCRIPTION
                "The frequency of VCCV packet.
                 Options:
                 1. freq1000ms(1000)   -indicates VCCV PING frequency, interval is 1000 ms
                 2. freq2000ms(2000)   -indicates VCCV PING frequency, interval is 2000 ms
                 3. freq5000ms(5000)   -indicates VCCV PING frequency, interval is 5000 ms
                 4. freq10000ms(10000) -indicates VCCV PING frequency, interval is 10000 ms
                "        
            DEFVAL { freq1000ms }
            ::= { hwPwAutoVccvEntry 2 }
        
        hwPwAutoVccvTimeoutLimit OBJECT-TYPE
            SYNTAX Unsigned32 (3..16)
            MAX-ACCESS read-write
            STATUS current
            DESCRIPTION
                "The timeout limit of VCCV ping.
                 Range: 3-16
                " 
            DEFVAL { 3 }
            ::= { hwPwAutoVccvEntry 3 }

        hwPwAutoVccvRecoverLimit OBJECT-TYPE
            SYNTAX Unsigned32 (1..16)
            MAX-ACCESS read-write
            STATUS current
            DESCRIPTION
                "The recover limit of VCCV ping.
                 Range: 1-16
                " 
            DEFVAL { 1 }                
            ::= { hwPwAutoVccvEntry 4 }

        hwPwAutoVccvRemotePwID OBJECT-TYPE
            SYNTAX Unsigned32 (1..4294967295)
            MAX-ACCESS read-write
            STATUS current
            DESCRIPTION
                "Indicates the PW Remote VcID in MH-PW.
                 Range: 1-4294967295.  
                 When this leaf is set to 4294967295, it means that no remote PW ID is configured in the case of no creation, 
                 and that the configuration of remote PW ID is canceled in the case of modify operation.                 
                "
            ::= { hwPwAutoVccvEntry 5 }
                
        hwPwAutoVccvRemoteIpAddress OBJECT-TYPE
            SYNTAX IpAddress
            MAX-ACCESS read-write
            STATUS current
            DESCRIPTION
                "Indicates the PW Remote IP address in MH-PW.
                "
            ::= { hwPwAutoVccvEntry 6 }
                    
        hwPwAutoVccvTtl OBJECT-TYPE
            SYNTAX Unsigned32 (0..255)
            MAX-ACCESS read-write
            STATUS current
            DESCRIPTION
                "Indicates the PW TTL value.
                 Range: 0-255.
                 When this leaf is set to 0, it means that no ttl value is configured in the case of no creation,
                 and that the configuration of TTL value is canceled in the case of modify operation.                 
                "
            ::= { hwPwAutoVccvEntry 7 }

        hwPwAutoVccvPingStatus OBJECT-TYPE
            SYNTAX INTEGER
                {
                    normal(0),
                    break(1),
                    inactive(2)
                }
            MAX-ACCESS read-only
            STATUS current
            DESCRIPTION
                "Indicates the VCCV ping status.
                 Options:
                 1. normal(0)   -indicates that VCCV PING can get reply from the peer and the PW connection is normal
                 2. break(1)    -indicates that VCCV PING cannot reach the peer and the PW connection is break
                 3. inactive(2) -indicates that VCCV PING is not in work mode
                "
            ::= { hwPwAutoVccvEntry 8 }
            
        hwPwAutoVccvPingSuccessNum OBJECT-TYPE
            SYNTAX Unsigned32 (0..4294967295)
            MAX-ACCESS read-only
            STATUS current
            DESCRIPTION
                "The number of VCCV ping succeed.
                 Range: 0-4294967295
                "
            ::= { hwPwAutoVccvEntry 9 }

        hwPwAutoVccvPingTimeOutNum OBJECT-TYPE
            SYNTAX Unsigned32 (0..4294967295)
            MAX-ACCESS read-only
            STATUS current
            DESCRIPTION
                "The number of VCCV ping time out.
                 Range: 0-4294967295
                "
            ::= { hwPwAutoVccvEntry 10 }

        hwPwAutoVccvStatisticsReset OBJECT-TYPE
       		SYNTAX INTEGER
       		    { 
       		        reset(1) 
       		    }
       		MAX-ACCESS read-write
       		STATUS     current
       		DESCRIPTION
             	"Clear the traffic statistics of this pw.
              	 Options:
              	 1. reset(1) -reset the traffic statistics of this PW
             	"
            ::= { hwPwAutoVccvEntry 11 }    


        hwPwAutoVccvPipeUniform OBJECT-TYPE
           SYNTAX INTEGER
                { 
                pipe(1),
                uniform(2)       
                }
            MAX-ACCESS read-write
            STATUS current
            DESCRIPTION
                "For setting VCCV ping mode.
                 Options:
                 1. pipe(1)    -indicates pipe mode of the VCCV ping.
                 2. uniform(2) -indicates uniform mode of the VCCV ping. 
                 Default: pipe(1)
                "  
            ::= { hwPwAutoVccvEntry 12 }               
            
        hwPwAutoVccvRowStatus OBJECT-TYPE
            SYNTAX RowStatus
            MAX-ACCESS read-write
            STATUS current
            DESCRIPTION
                "For creating and modifying this row. None of the 
                 read-create objects in the conceptual rows may be changed  
                 when this object is in the active(1) state.
                 Options:
                 1. active(1)      -indicates query operation
                 2. createAndGo(4) -indicates creating an auto VCCV PING configuration
                 3. destroy(6)     -indicates deleting an auto VCCV PING configuration
                "
            ::= { hwPwAutoVccvEntry 13 }  
                     

        hwPwCmdConformance OBJECT IDENTIFIER ::= { hwPwCmdMIB 3 }
        
        hwPwCmdGroups OBJECT IDENTIFIER ::= { hwPwCmdConformance 1 }
        
        hwPwCmdVcGroup OBJECT-GROUP
            OBJECTS { hwPwCmdVcIndexNext, hwPwCmdVcPeerAddr, hwPwCmdVcTemplateIndex, 
                hwPwCmdVcIfIndex, hwPwCmdVcCw, hwPwCmdVcSecondary, hwPwCmdVcAcStatus, 
                hwPwCmdVcSignalProtocol, hwPwCmdVcUpTime, hwPwCmdVcType, 
                hwPwCmdVcBandwidth, hwPwCmdVcPeerAddrType, hwPwCmdVcStatus, 
                hwPwCmdVcMaxAtmCells, hwPwCmdVcGroupID, hwPwCmdVcMtu, hwPwCmdVcRowStatus, 
                hwPwCmdVcID, hwPwCmdVcQoSBehaviorIndex, hwPwCmdVcTnlPolicyName, 
                hwPwCmdVcIpInterworking, hwPwCmdVcExplicitPathName, hwPwCmdVcInboundLabel, 
                hwPwCmdVcOutboundLabel, hwPwCmdVcVCCV, hwPwCmdVcSwitchID, 
                hwPwCmdVcSwitchPeerAddrType, hwPwCmdVcSwitchPeerAddr, hwPwCmdVcSwitchInboundLabel, 
                hwPwCmdVcSwitchOutboundLabel }
            STATUS current
            DESCRIPTION 
                "Collection of objects that are required in all  
                 implementations that support the PW CMD MIB module.
                "
            ::= { hwPwCmdGroups 1 }
        
        hwPwCmdRemoteVcGroup OBJECT-GROUP
            OBJECTS { hwPwCmdRemoteVcID, hwPwCmdRemoteVcType, hwPwCmdRemoteVcMtu, hwPwCmdRemoteVcGroupID, 
                      hwPwCmdRemoteVcMaxAtmCells, hwPwCmdRemoteVcCw, hwPwCmdRemoteVcNotif, hwPwCmdRemoteVcStatus, 
                      hwPwCmdRemoteVcSwitchID, hwPwCmdRemoteVcSwitchType, hwPwCmdRemoteVcSwitchMtu, 
                      hwPwCmdRemoteVcSwitchGroupID, hwPwCmdRemoteVcSwitchMaxAtmCells, hwPwCmdRemoteVcSwitchCw, 
                      hwPwCmdRemoteVcSwitchNotif, hwPwCmdRemoteVcSwitchStatus }
            STATUS current
            DESCRIPTION 
                "Collection of objects that are required by remote PW.
                "
            ::= { hwPwCmdGroups 2 }
        
        hwPwCmdTemplateGroup OBJECT-GROUP
            OBJECTS { hwPwCmdTemplateVcType, hwPwCmdTemplateIndexNext, hwPwCmdTemplateBandwidth, 
                hwPwCmdTemplatePeerAddrType, hwPwCmdTemplateName, hwPwCmdTemplatePeerAddr, 
                hwPwCmdTemplateMtu, hwPwCmdTemplateVCCV, hwPwCmdTemplateFrag, hwPwCmdTemplateCw, 
                hwPwCmdTemplateRowStatus, hwPwCmdTemplateIpInterworking, hwPwCmdTemplateQoSBehaviorIndex, 
                hwPwCmdTemplateTnlPolicyName, hwPwCmdTemplateExplicitPathName }
            STATUS current
            DESCRIPTION 
                "Collection of objects required to perform pw template related commands.
                "
            ::= { hwPwCmdGroups 3 }
        
        hwPwCmdOperGroup OBJECT-GROUP
            OBJECTS { hwPwCmdOperType, hwPwCmdOperVcOrPwtIndex, hwPwCmdOperStatus, 
                hwPwCmdOperRowStatus, hwPwCmdOperTimeStamp }
            STATUS current
            DESCRIPTION 
                "Collection of objects required to perform pw reset related commands.
                "
            ::= { hwPwCmdGroups 4 }
        
        hwPwCmdVcNotificationControlGroup OBJECT-GROUP
            OBJECTS { hwPwCmdVcSwitchNotifEnable }
            STATUS current
            DESCRIPTION 
                "Collection of objects for controlling the PW notifications.
                "
            ::= { hwPwCmdGroups 6 }
        
        hwPwCmdVcNotificationGroup NOTIFICATION-GROUP
            NOTIFICATIONS { hwPwCmdVcSwitchWtoP, hwPwCmdVcSwitchPtoW }
            STATUS current
            DESCRIPTION 
                "Collection PW notifications objects.
                "
            ::= { hwPwCmdGroups 7 }
            
        hwPwCmdTrapsVbOids OBJECT IDENTIFIER ::= { hwPwCmdMIB 4 }                    
            hwPwCmdTunnId OBJECT-TYPE
            SYNTAX Integer32 (1..64)
            MAX-ACCESS accessible-for-notify
            STATUS current
            DESCRIPTION
                "Indicates the index of tunnel.
                 Range: 1-64
                "
            ::= { hwPwCmdTrapsVbOids 1 }                                
            
        hwPwCmdTraps OBJECT IDENTIFIER ::= { hwPwCmdMIB 5 }
        
        hwPwCmdCommonTraps OBJECT IDENTIFIER ::= { hwPwCmdTraps 1 }
        
        hwPwCmdCommonTrapsPrefix OBJECT IDENTIFIER ::= { hwPwCmdCommonTraps 0 }
        
        hwPwCmdPwStatus NOTIFICATION-TYPE
            OBJECTS { 
                      hwPwCmdPwID,                  -- index of pw
                      hwPwCmdPwVcStatus             -- vc status of pw
                    }
            STATUS current
            DESCRIPTION 
                "This notification is generated when the pw's status 
                 changed.
                "
            ::= { hwPwCmdCommonTraps 0 1 }
            
        hwPwCmdPwDeleted NOTIFICATION-TYPE
            OBJECTS {
                      pwIndex,                 -- index of pw
                      pwType,                  -- type of pw
                      pwID,                    -- identifier of pw
                      pwPeerAddrType,          -- the address type of the pw's peer
                      pwPeerAddr               -- the address of the pw's peer
                    }
            STATUS current
            DESCRIPTION 
                "This notification is generated when the pw's deleted.
                "
            ::= { hwPwCmdCommonTraps 0 2 }

        hwPwCmdAlarmTraps OBJECT IDENTIFIER ::= { hwPwCmdTraps 2 }
        
        hwPwCmdAlarmTrapsPrefix OBJECT IDENTIFIER ::= { hwPwCmdAlarmTraps 0 }
        
        hwPwCmdSerRecov NOTIFICATION-TYPE
            OBJECTS { 
                      pwIndex,                  -- the first PW index
                      pwIndex                   -- the last PW index
                    }
            STATUS current
            DESCRIPTION 
                "This notification is generated when the pw recovered 
                 the service.
                 The first object is the index of the first pw, 
                 and the other is the index of the last pw.
                "
            ::= { hwPwCmdAlarmTraps 0 1 }
        
        hwPwCmdSerFault NOTIFICATION-TYPE
            OBJECTS { 
                      pwIndex,                  -- the first PW index
                      pwIndex                   -- the last PW index
                    }
            STATUS current
            DESCRIPTION 
                "This notification is generated when the pw service 
                 has some faults.
                 The first object is the index of the first pw, 
                 and the other is the index of the last pw.
                "
            ::= { hwPwCmdAlarmTraps 0 2 }
        
        hwPwCmdSerSwitchToSec NOTIFICATION-TYPE
            OBJECTS { 
                      pwIndex,                  -- index of primary  pw
                      pwIndex                   -- index of secondary pw
                    }
            STATUS current
            DESCRIPTION 
                "This notification is generated when the service 
                 switches over to the secondary PW.
                 The first object is the index of primary pw, 
                 and the other is the index of secondary pw. 
                "
            ::= { hwPwCmdAlarmTraps 0 3 }
        
        hwPwCmdSerSwitchToPri NOTIFICATION-TYPE
            OBJECTS { 
                      pwIndex,                  -- index of primary pw
                      pwIndex                   -- index of secondary pw
                    }
            STATUS current
            DESCRIPTION 
                "This notification is generated when the service 
                 switches over to the primary PW.
                 The first object is the index of primary pw, 
                 and the other is the index of secondary pw.
                "
            ::= { hwPwCmdAlarmTraps 0 4 }
        
        hwPwCmdTunnSwitchToW NOTIFICATION-TYPE
            OBJECTS { 
                      hwPwCmdTunnId,                  -- index of protect-tunnel
                      hwPwCmdTunnId                   -- index of work-tunnel
                    }
            STATUS current
            DESCRIPTION 
                "This notification is generated when the MPLS 
                 service switches from the protect tunnel to the 
                 work tunnel.
                 The first object is the index of work-tunnel, 
                 and the other is the index of protect-tunnel.
                "
            ::= { hwPwCmdAlarmTraps 0 5 }
        
        hwPwCmdTunnSwitchToP NOTIFICATION-TYPE
            OBJECTS { 
                      hwPwCmdTunnId,                  -- index of work-tunnel
                      hwPwCmdTunnId                   -- index of protect-tunnel
                    }
            STATUS current
            DESCRIPTION 
                "This notification is generated when the MPLS 
                 service switches from the work-tunnel to the 
                 protect-tunnel.
                 The first object is the index of protect-tunnel, 
                 and the other is the index of work-tunnel.
                "
            ::= { hwPwCmdAlarmTraps 0 6 }
                   
    END
