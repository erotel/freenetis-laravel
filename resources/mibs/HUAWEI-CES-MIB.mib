--  ============================================================================
-- Copyright (C) 2013 by  HUAWEI TECHNOLOGIES. All rights reserved.
-- Description:  The MIB is used for defining Huawei's CES management MIB objects,
--               which provides CES management NMS interfaces.
-- Reference:
-- Version: V3.17
-- ============================================================================

    HUAWEI-CES-MIB DEFINITIONS ::= BEGIN
 
        IMPORTS
            hwFrameIndex, hwSlotIndex, hwFrameIndex, hwSlotIndex, hwPortIndex, hwConfigChangeIP
                FROM HUAWEI-DEVICE-MIB          
            huaweiMgmt          
                FROM HUAWEI-MIB         
            ifIndex         
                FROM IF-MIB         
            Unsigned32, Gauge32, Counter32, OBJECT-TYPE, Integer32,MODULE-IDENTITY,NOTIFICATION-TYPE
                FROM SNMPv2-SMI         
            RowStatus, DateAndTime
                FROM SNMPv2-TC;
                                                                
        hwCes     MODULE-IDENTITY
            LAST-UPDATED "201301040900Z"
            ORGANIZATION "Huawei Technologies Co., Ltd."
            CONTACT-INFO 
                   "Huawei Industrial Base
                    Bantian, Longgang
                    Shenzhen 518129
                    People's Republic of China
                    Website: http://www.huawei.com
                    Email: support@huawei.com
                   "
            DESCRIPTION  "The MIB is used for defining Huawei's CES management MIB objects, 
                          which provides CES management NMS interfaces.
                         " 
--  Revision history
            REVISION     "201301040900Z"  
            DESCRIPTION  "V3.17, changes in this revision:
                          Add a new table hwCesOnuTDMVCLCfgTable.
                         " 
                         
            REVISION     "201102090900Z"  
            DESCRIPTION  "V3.16, changes in this revision:
                          modify the description of the leaf node hwAtmCesPortCfgState.
                          modify the description of the leaf node hwAtmCesPortCESoPCLKBindPW.
                         " 

            REVISION     "201009270900Z"  
            DESCRIPTION  "V3.15, changes in this revision:
                          modify the description of the whole MIB file.
                         "  

            REVISION     "201009070900Z"  
            DESCRIPTION  "V3.14, changes in this revision:
                          Add the definition of the leaf node hwAtmCesPortStatus.
                          Modify the definition of the trap node hwCesPortStatusTrap.
                         "  

            REVISION     "201006300900Z"  
            DESCRIPTION  "V3.13, changes in this revision:
                          Add the definition of the trap node,include: hwCesBoardWorkModeChangeTrap, 
                          hwCesPortWorkModeChangeTrap, hwCesACMClockFaultAlarmTrap for trap optimization.
                         "  

            REVISION     "201005280900Z"  
            DESCRIPTION  "V3.12, changes in this revision:
                          Add leaf node hwAtmCesPortCfgWorkMode for setting or obtaining the working mode of the port.
                          Add leaf node hwAtmCesPortCfgClockMode for setting or obtaining the clock mode of the port.
                          Add leaf node hwAtmCesPortCfgSignalType for setting or obtaining the signal type of the port.
                          Add leaf node hwAtmCesPortCfgFrameVerifyMode for setting or obtaining frame verify mode of port.
                          Add leaf node hwAtmCesPortCfgLiuStatus for obtaining LIU port state.
                          Add leaf node hwAtmCesPortCfgImpedance for setting and obtaining impedance of port.
                          Add leaf node hwAtmCesPortLineCode for setting and obtaining configuration of the line encoding type.
                          Add leaf node hwAtmCesPortAcmSource for setting and obtaining configuration of adaptive clock source.
                          Add leaf node hwAtmCesPortV35CfgBlockStatus for blocking or unblocking the port, 
                          or inquiring the block state.
                          Add leaf node hwAtmCesPortMaintOper for setting or obtaining the operation of looping test mode.
                          Add leaf node hwAtmCesPortCfgState in table hwAtmCesPortCfgTable. 
                          for getting the configuration status of the subscriber type.
                         "  
                         
            REVISION     "201004190900Z"  
            DESCRIPTION  "V3.11, changes in this revision:
                          Modify the errors of the MIB file for MIB standardization.
                         "
                         
            REVISION     "201002080900Z"  
            DESCRIPTION  "V3.10, changes in this revision:
                          Modify the definition of the trap node,include:
                          hwCesPortSignalLossAlarmTrap
                          hwCesFrameLossAlarmTrap
                          hwCesRemoteAlarmReceivedAlarmTrap
                          hwCesMultiframeLossAlarmTrap
                          hwCesSignalOccurAlarmTrap
                          hwCesCRC4ErrorOccurAlarmTrap
                          hwCesLOSRecoverAlarmTrap
                          hwCesFrameRecoverAlarmTrap
                          hwCesRemoteAlarmRecoverAlarmTrap
                          hwCesMultiframeRecoverAlarmTrap
                          hwCesSignalRecoverAlarmTrap       
                          hwCesCRC4RecoverAlarmTrap 
                         "  

            REVISION     "201001120900Z"  
            DESCRIPTION  "V3.09, changes in this revision:
                          Add hwCesPortStatusTrap for indicating alarm when Ces port status changes.             
                          Add hwCesPortSignalLossAlarmTrap indicating alarm when loss of signal occurs at the E1/T1 port      
                          Add hwCesFrameLossAlarmTrap indicating alarm when Loss of frame alignment occurs at the E1/T1 port.          
                          Add hwCesRemoteAlarmReceivedAlarmTrap indicating alarm for receving remote alarm occurs at the E1/T1 port. 
                          Add hwCesMultiframeLossAlarmTrap indicating alarm when Loss of multiframe alignment occurs at the E1/T1 port.     
                          Add hwCesSignalOccurAlarmTrap for sending trap indication signal occurs at the E1/T1 port.         
                          Add hwCesCRC4ErrorOccurAlarmTrap indicating alarm when CRC4 error occurs at the E1/T1 port.     
                          Add hwCesLOSRecoverAlarmTrap indicating alarm when Loss of signal(LOS) recovers at the E1/T1 port.          
                          Add hwCesFrameRecoverAlarmTrap indicating alarm when Loss of frame recovers at the E1/T1 port.       
                          Add hwCesRemoteAlarmRecoverAlarmTrap indicating alarm when remote alarm recovers at the E1/T1 port. 
                          Add hwCesMultiframeRecoverAlarmTrap indicating alarm when loss of multiframe alignment recovers at the E1/T1 port.  
                          Add hwCesSignalRecoverAlarmTrap for sending trap indication signal recover at the E1/T1 port.       
                          Add hwCesCRC4RecoverAlarmTrap indicating alarm when CRC4 recovers at the E1/T1 port.         
                          Add hwCesACMClockRestoreAlarmTrap indicating alarm when ACM clock restores.
                         " 

            REVISION     "200911230900Z"  
            DESCRIPTION  "V3.08, changes in this revision:
                          Modify the range of leaf node hwAtmCesPortCESoPCLKIndex form <0, 1> to <0, 15>.
                          Add enum b8zs(3) in leaf node hwAtmCesPortLineCode.
                          Add enum ohm_100(3) in leaf node hwAtmCesPortCfgImpedance.
                          Add leaf node hwAtmCesCfgAccessMode in table hwAtmCesCfgTable for setting board working mode.    
                         " 
                         
            REVISION     "200805230900Z"  
            DESCRIPTION  "V3.03, changes in this revision: 
                          Delete the scalar hwCesDefinedSuccessiveSeriousErroredSeconds.
                          Modify the name of leaf node hwAtmCesPortCfgE1PortReset to hwAtmCesPortAdminStatus.
                         "
            
            REVISION     "200304280900Z"  
            DESCRIPTION  "V3.00, changes in this revision:
                          Modify description of the leaf nodes.
                         "
                                                
            REVISION     "200201220900Z"  
            DESCRIPTION  "V1.00, Initial version."
            ::= { huaweiMgmt 11 }   
    
-- Node definitions 
        -- 1.3.6.1.4.1.2011.5.11.1
        hwAtmCesServDescrExtTable OBJECT-TYPE
            SYNTAX SEQUENCE OF HwAtmCesServDescrExtEntry
            MAX-ACCESS not-accessible
            STATUS     current
            DESCRIPTION
                "CES service description extended table.
                 This table is used during the creation of the connection between the CES-SDT port and the CES-V35 port.     
                 The index of this table is ifIndex. 
                "
            ::= { hwCes 1 }
        
        -- 1.3.6.1.4.1.2011.5.11.1.1
        hwAtmCesServDescrExtEntry OBJECT-TYPE
            SYNTAX HwAtmCesServDescrExtEntry
            MAX-ACCESS not-accessible
            STATUS     current
            DESCRIPTION
                "CES service description extended table.
                 This table is used during the creation of the connection between the CES-SDT port and the CES-V35 port.    
                 The index of this entry is ifIndex.
                "
            INDEX { ifIndex }
            ::= { hwAtmCesServDescrExtTable 1 }
        
        HwAtmCesServDescrExtEntry ::=
            SEQUENCE 
                { 
                hwAtmCesServDescrExtNValue
                    Integer32,
                hwAtmCesServDescrExtBitMap
                    Unsigned32,
                hwAtmCesServDescrExtFillRate
                    Integer32,
                hwAtmCesServDescrExtRowStatus
                    RowStatus
                }

        -- 1.3.6.1.4.1.2011.5.11.1.1.1
        hwAtmCesServDescrExtNValue OBJECT-TYPE
            SYNTAX     Integer32 (1..32)
            MAX-ACCESS read-create
            STATUS     current
            DESCRIPTION
                "The N value of V35 port."
            ::= { hwAtmCesServDescrExtEntry 1 }
        
        -- 1.3.6.1.4.1.2011.5.11.1.1.2
        hwAtmCesServDescrExtBitMap OBJECT-TYPE
            SYNTAX     Unsigned32 (2..4294967294)
            MAX-ACCESS read-create
            STATUS     current
            DESCRIPTION
                "The timeslot bitmap in SDT mode."
            ::= { hwAtmCesServDescrExtEntry 2 }
        
        -- 1.3.6.1.4.1.2011.5.11.1.1.3
        hwAtmCesServDescrExtFillRate OBJECT-TYPE
            SYNTAX     Integer32 (20..47)
            MAX-ACCESS read-create
            STATUS     current
            DESCRIPTION
                "The fillrate of cell."
            ::= { hwAtmCesServDescrExtEntry 3 }
        
        -- 1.3.6.1.4.1.2011.5.11.1.1.4
        hwAtmCesServDescrExtRowStatus OBJECT-TYPE
            SYNTAX     RowStatus
            MAX-ACCESS read-create
            STATUS     current
            DESCRIPTION
                "This object is used to create a
                 new row or modify or delete an
                 existing row in this table.
                 createAndGo(4),destroy(6)
                "
            ::= { hwAtmCesServDescrExtEntry 4 }
        
        -- 1.3.6.1.4.1.2011.5.11.2
        hwAtmCesCfgTable OBJECT-TYPE
            SYNTAX SEQUENCE OF HwAtmCesCfgEntry
            MAX-ACCESS not-accessible
            STATUS     current
            DESCRIPTION
                "CES board configration table. 
                 The indexes of this table are hwFrameIndex and hwSlotIndex.
                "
            ::= { hwCes 2 }
        
        -- 1.3.6.1.4.1.2011.5.11.2.1
        hwAtmCesCfgEntry OBJECT-TYPE
            SYNTAX HwAtmCesCfgEntry
            MAX-ACCESS not-accessible
            STATUS     current
            DESCRIPTION          
                "CES board configration table.
                 The indexes of this entry are hwFrameIndex and hwSlotIndex.
                "
            INDEX { hwFrameIndex, hwSlotIndex }
            ::= { hwAtmCesCfgTable 1 }
                 
        HwAtmCesCfgEntry ::=
            SEQUENCE 
                { 
                hwAtmCesCfgWorkMode
                    INTEGER,
                hwAtmCesCfgDDNClockMode
                    INTEGER,
                hwAtmCesCfgDDNClockSrcPort
                    Integer32,
                hwAtmCesCfgE1GroupType0
                    INTEGER,
                hwAtmCesCfgE1GroupType1
                    INTEGER,
                hwAtmCesCfgE1GroupType2
                    INTEGER,
                hwAtmCesCfgE1GroupType3
                    INTEGER,
                hwAtmCesCfgAccessMode
                    INTEGER
                }

        -- 1.3.6.1.4.1.2011.5.11.2.1.1
        hwAtmCesCfgWorkMode OBJECT-TYPE
            SYNTAX     INTEGER
                {
                tdm(1),
                e1(2),
                v35(3),
                idle(4),
                indep(5)
                }
            MAX-ACCESS read-write
            STATUS     current
            DESCRIPTION
                "CES board working mode.
                 Options:
                 1. tdm(1)  - CES board working mode is tdm
                 2. e1(2)   - CES board working mode is e1
                 3. v35(3)  - CES board working mode is v35
                 4. idle(4) - CES board working mode is idle
                 5. indep(5) - CES board working mode is indep                 
                "
            ::= { hwAtmCesCfgEntry 1 }
        
        -- 1.3.6.1.4.1.2011.5.11.2.1.2
        hwAtmCesCfgDDNClockMode OBJECT-TYPE
            SYNTAX     INTEGER
                {
                line(1),
                srts(2)
                }
            MAX-ACCESS read-write
            STATUS     current
            DESCRIPTION
                "The DDN clock mode of CES board.
                 Options:
                 1. line(1)  - The DDN clock mode of CES board is line
                 2. srts(2)  - The DDN clock mode of CES board is srts
                "
            ::= { hwAtmCesCfgEntry 2 }
        
        -- 1.3.6.1.4.1.2011.5.11.2.1.3
        hwAtmCesCfgDDNClockSrcPort OBJECT-TYPE
            SYNTAX     Integer32 (0..15)
            MAX-ACCESS read-write
            STATUS     current
            DESCRIPTION
                "The DDN clock source of CES board."
            ::= { hwAtmCesCfgEntry 3 }
        
        -- 1.3.6.1.4.1.2011.5.11.2.1.4
        hwAtmCesCfgE1GroupType0 OBJECT-TYPE
            SYNTAX     INTEGER
                {
                cesE1(1),
                tdmE1(2),
                ddnE1(3)
                }
            MAX-ACCESS read-write
            STATUS     current
            DESCRIPTION
                "E1 Group 0 (port 0~3) work mode.
                 Options:
                 1. cesE1(1) - E1 work mode is cesE1
                 2. tdmE1(2) - E1 work mode is tdmE1
                 3. ddnE1(3) - E1 work mode is ddnE1
                "
            ::= { hwAtmCesCfgEntry 4 }
        
        -- 1.3.6.1.4.1.2011.5.11.2.1.5
        hwAtmCesCfgE1GroupType1 OBJECT-TYPE
            SYNTAX     INTEGER
                {
                cesE1(1),
                tdmE1(2),
                ddnE1(3)
                }
            MAX-ACCESS read-write
            STATUS     current
            DESCRIPTION
                "E1 Group 1 (port 4~7) work mode.
                 Options:
                 1. cesE1(1) - E1 work mode is cesE1
                 2. tdmE1(2) - E1 work mode is tdmE1
                 3. ddnE1(3) - E1 work mode is ddnE1                
                "
            ::= { hwAtmCesCfgEntry 5 }
        
        -- 1.3.6.1.4.1.2011.5.11.2.1.6
        hwAtmCesCfgE1GroupType2 OBJECT-TYPE
            SYNTAX     INTEGER
                {
                cesE1(1),
                tdmE1(2),
                ddnE1(3)
                }
            MAX-ACCESS read-write
            STATUS     current
            DESCRIPTION
                "E1 Group 2 (port 8~11) work mode.
                 Options:
                 1. cesE1(1) - E1 work mode is cesE1
                 2. tdmE1(2) - E1 work mode is tdmE1
                 3. ddnE1(3) - E1 work mode is ddnE1                   
                "
            ::= { hwAtmCesCfgEntry 6 }
        
        -- 1.3.6.1.4.1.2011.5.11.2.1.7
        hwAtmCesCfgE1GroupType3 OBJECT-TYPE
            SYNTAX     INTEGER
                {
                cesE1(1),
                tdmE1(2),
                ddnE1(3)
                }
            MAX-ACCESS read-write
            STATUS     current
            DESCRIPTION
                "E1 Group 3 (port 12~15) work mode.
                 Options:
                 1. cesE1(1) - E1 work mode is cesE1
                 2. tdmE1(2) - E1 work mode is tdmE1
                 3. ddnE1(3) - E1 work mode is ddnE1                   
                "
            ::= { hwAtmCesCfgEntry 7 }
        -- 1.3.6.1.4.1.2011.5.11.2.1.8
        hwAtmCesCfgAccessMode OBJECT-TYPE
            SYNTAX     INTEGER
                {
                e1(1),
                t1(2)
                }
            MAX-ACCESS read-write
            STATUS     current
            DESCRIPTION
                "Board work mode.
                 Options:
                 1. e1(1) - E1
                 2. t1(2) - T1
                "
            ::= { hwAtmCesCfgEntry 8 }              
        
        -- 1.3.6.1.4.1.2011.5.11.3
        hwAtmCesPortCfgTable OBJECT-TYPE
            SYNTAX SEQUENCE OF HwAtmCesPortCfgEntry
            MAX-ACCESS not-accessible
            STATUS     current
            DESCRIPTION
                "Port configration table of CES board. The table is used to port configration
                 of CES board.
                 The index of this table is ifIndex.
                "
            ::= { hwCes 3 }
        
        -- 1.3.6.1.4.1.2011.5.11.3.1
        hwAtmCesPortCfgEntry OBJECT-TYPE
            SYNTAX HwAtmCesPortCfgEntry
            MAX-ACCESS not-accessible
            STATUS     current
            DESCRIPTION          
                "Port configration table of CES board. The table is used to port configration
                 of CES board.
                 The index of this entry is ifIndex.
                "
            INDEX { ifIndex }
            ::= { hwAtmCesPortCfgTable 1 }
        
        HwAtmCesPortCfgEntry ::=
            SEQUENCE { 
                hwAtmCesPortCfgWorkMode
                    INTEGER,
                hwAtmCesPortCfgClockMode
                    INTEGER,
                hwAtmCesPortCfgSignalType
                    INTEGER,
                hwAtmCesPortCfgFrameVerifyMode
                    INTEGER,
                hwAtmCesPortTimeSlotBMP
                    Unsigned32,
                hwAtmCesPortCfgWarningStatus
                    Unsigned32,
                hwAtmCesPortCfgUtopiaStatus
                    INTEGER,
                hwAtmCesPortCfgLiuStatus
                    INTEGER,
                hwAtmCesPortCfgImpedance
                    INTEGER,
                hwAtmCesPortCfgPhyState
                    INTEGER,
                hwAtmCesPortCfgLoopLineState
                    INTEGER,
                hwAtmCesPortCfgE1Frametype
                    INTEGER,
                hwAtmCesPortAdminStatus
                    INTEGER,
                hwAtmCesPCMErrorReportAlarm
                    Unsigned32,
                hwAtmCesPortCfgESAlarmThreshold
                    Integer32,
                hwAtmCesPortCfgCSESAlarmThreshold
                    Integer32,
                hwAtmCesPortCfgDMAlarmThreshold
                    Integer32,
                hwAtmCesPortLineCode
                    INTEGER,
                hwAtmCesPortAcmSource
                    Integer32,
                hwAtmCesPortCfgState
                    INTEGER                 
             }

        -- 1.3.6.1.4.1.2011.5.11.3.1.1
        hwAtmCesPortCfgWorkMode OBJECT-TYPE
            SYNTAX     INTEGER
                {
                uni(1),
                sdt(2),
                udt(3),
                idle(4),
                ima(5),
                invalidMode(-1)
                }
            MAX-ACCESS read-write
            STATUS     current
            DESCRIPTION
                "The working mode of port.
                 Options:
                 1. uni(1)          - UNI mode
                 2. sdt(2)          - SDT mode
                 3. udt(3)          - UDT mode
                 4. idle(4)         - Idle mode
                 5. ima(5)          - IMA mode
                 6. invalidMode(-1) - Invalid mode
                "
            ::= { hwAtmCesPortCfgEntry 1 }
        
        -- 1.3.6.1.4.1.2011.5.11.3.1.2
        hwAtmCesPortCfgClockMode OBJECT-TYPE
            SYNTAX     INTEGER
                {
                system(1),
                line(2),
                acm(3),
                srts(4),
                invalidClock(-1)
                }
            MAX-ACCESS read-write
            STATUS     current
            DESCRIPTION
                "The clock mode of port.
                 Options:
                 1. system(1)        - System clock
                 2. line(2)          - Line clock
                 3. acm(3)           - Acm clock
                 4. srts(4)          - Srts clock
                 5. invalidClock(-1) - Invalid clock
                "
            ::= { hwAtmCesPortCfgEntry 2 }
        
        -- 1.3.6.1.4.1.2011.5.11.3.1.3
        hwAtmCesPortCfgSignalType OBJECT-TYPE
            SYNTAX     INTEGER
                {
                ccs(1),
                cas(2),
                invalidSignal(-1)
                }
            MAX-ACCESS read-write
            STATUS     current
            DESCRIPTION
                "Signal type of port.
                 Options:
                 1. ccs(1)            - CCS signal
                 2. cas(2)            - CAS signal 
                 3. invalidSignal(-1) - Invalid signal
                "
            ::= { hwAtmCesPortCfgEntry 3 }
        
        -- 1.3.6.1.4.1.2011.5.11.3.1.4
        hwAtmCesPortCfgFrameVerifyMode OBJECT-TYPE
            SYNTAX     INTEGER
                {
                enable(1),
                disable(2),
                invalidOrNotSupport(-1)
                }
            MAX-ACCESS read-write
            STATUS     current
            DESCRIPTION
                "Frame verify mode of port.
                 Options:
                 1. enable(1)               - Open frame verify
                 2. disable(2)              - Close frame verify
                 3. invalidOrNotSupport(-1) - Invalid or does not support frame verify 
                "
            ::= { hwAtmCesPortCfgEntry 4 }
        
        -- 1.3.6.1.4.1.2011.5.11.3.1.5
        hwAtmCesPortTimeSlotBMP OBJECT-TYPE
            SYNTAX Unsigned32 (0 | 2..4294967294)
            MAX-ACCESS read-only
            STATUS     current
            DESCRIPTION
                "Timeslot bitmap of port, 0 is the initial value of timeslot bitmap."
            ::= { hwAtmCesPortCfgEntry 5 }
        
        -- 1.3.6.1.4.1.2011.5.11.3.1.6
        hwAtmCesPortCfgWarningStatus OBJECT-TYPE
            SYNTAX     Unsigned32
            MAX-ACCESS read-only
            STATUS     current
            DESCRIPTION
                "Alarm state of port."
            ::= { hwAtmCesPortCfgEntry 6 }
        
        -- 1.3.6.1.4.1.2011.5.11.3.1.7
        hwAtmCesPortCfgUtopiaStatus OBJECT-TYPE
            SYNTAX     INTEGER
                {
                normal(1),
                test(2),
                idle(3),
                notExist(4),
                fail(5),
                block(6)
                }
            MAX-ACCESS read-only
            STATUS     current
            DESCRIPTION
                "UTOPIA port state.
                 Options:
                 1. normal(1)   - Normal state
                 2. test(2)     - Test state
                 3. idle(3)     - Idle state
                 4. notExist(4) - Does not exist
                 5. fail(5)     - Fail state
                 6. block(6)    - Block state
                "
            ::= { hwAtmCesPortCfgEntry 7 }
        
        -- 1.3.6.1.4.1.2011.5.11.3.1.8
        hwAtmCesPortCfgLiuStatus OBJECT-TYPE
            SYNTAX     INTEGER
                {
                normal(1),
                test(2),
                idle(3),
                notExisted(4),
                fail(5),
                block(6),
                maintain(7),
                localLoop(11),
                remoteLoop(12),
                tsLocalLoop(13),
                payLoadLoop(14),
                invalidStatus(-1)
                }
            MAX-ACCESS read-only
            STATUS     current
            DESCRIPTION
                "LIU port state.
                 Options:
                 1.  normal(1)         - Normal state
                 2.  test(2)           - Test state
                 3.  idle(3)           - Idle state
                 4.  notExisted(4)     - Does not exist
                 5.  fail(5)           - Fail state
                 6.  block(6)          - Block state
                 7.  maintain(7)       - Maintain state
                 8.  localLoop(11)     - Local-loop state 
                 9.  remoteLoop(12)    - Remote-loop state
                 10. tsLocalLoop(13)   - ts-Localloop state
                 11. payLoadLoop(14)   - Payload-loop state
                 12. invalidStatus(-1) - Invalid state
                "
            ::= { hwAtmCesPortCfgEntry 8 }
        
        -- 1.3.6.1.4.1.2011.5.11.3.1.9
        hwAtmCesPortCfgImpedance OBJECT-TYPE
            SYNTAX     INTEGER
                {
                ohm75(1),
                ohm120(2),
                ohm100(3),
                invalidImpedance(-1)
                }
            MAX-ACCESS read-write
            STATUS     current
            DESCRIPTION
                "Impedance of port.
                 Options:
                 1. ohm75(1)             - 75 ohm
                 2. ohm120(2)            - 120 ohm
                 3. ohm100(3)            - 100 ohm
                 4. invalidImpedance(-1) - Invalid impedance
                "
            ::= { hwAtmCesPortCfgEntry 9 }
        
        -- 1.3.6.1.4.1.2011.5.11.3.1.10
        hwAtmCesPortCfgPhyState OBJECT-TYPE
            SYNTAX     INTEGER
                {
                normal(0),
                fault(1),
                unknown(2)
                }
            MAX-ACCESS read-only
            STATUS     current
            DESCRIPTION
                "E1 port physical state.
                 Options:
                 1. normal(0)  - Normal state
                 2. fault(1)   - Fault state
                 3. unknown(2) - Unknown state
                "
            ::= { hwAtmCesPortCfgEntry 10 }
        
        -- 1.3.6.1.4.1.2011.5.11.3.1.11
        hwAtmCesPortCfgLoopLineState OBJECT-TYPE
            SYNTAX     INTEGER
                {
                synchronized(0),
                farEndAlarm(1),
                nearEndAlarm(2),
                testing(3),
                unknown(4)
                }
            MAX-ACCESS read-only
            STATUS     current
            DESCRIPTION
                "E1 port line state.
                 Options:
                 1. synchronized(0) - Synchronized state 
                 2. farEndAlarm(1)  - Far-End-Alarm state
                 3. nearEndAlarm(2) - Near-End-Alarm state
                 4. testing(3)      - Testing state
                 5. unknown(4)      - Unknown state
                "
            ::= { hwAtmCesPortCfgEntry 11 }
        
        -- 1.3.6.1.4.1.2011.5.11.3.1.12
        hwAtmCesPortCfgE1Frametype OBJECT-TYPE
            SYNTAX     INTEGER
                {
                pcm31(1),
                unframe(2)
                }
            MAX-ACCESS read-write
            STATUS     current
            DESCRIPTION
                "pvm-e1 port frame type.
                 Options:
                 1. pcm31(1)   - PCM31 frame
                 2. unframe(2) - It's not a frame   
                "
            ::= { hwAtmCesPortCfgEntry 12 }
        
        -- 1.3.6.1.4.1.2011.5.11.3.1.13
        hwAtmCesPortAdminStatus OBJECT-TYPE
            SYNTAX     INTEGER
                {
                reset(1),
                selfcheck(2)
                }
            MAX-ACCESS read-write
            STATUS     current
            DESCRIPTION
                "Port operation type.
                 Options:
                 1. reset(1)     - Reset port
                 2. selfcheck(2) - Self check
                "
            ::= { hwAtmCesPortCfgEntry 13 }
        
        -- 1.3.6.1.4.1.2011.5.11.3.1.14
        hwAtmCesPCMErrorReportAlarm OBJECT-TYPE
            SYNTAX     Unsigned32 (0..63)
            MAX-ACCESS read-only
            STATUS     current
            DESCRIPTION
                "PCM error report configuration.
                 bit0: report alarm when pcm line fault occurs;
                 bit1: set PCM fault and set port to OOS state when ULF exceeds the threshold;
                 bit2: set PCM fault and set port to OOS state when OLF exceeds the threshold;
                 bit3: report event when LDT exceeds the threshold;
                 bit4: report event when frame slip exceeds the threshold;
                 bit5: report event when line temporary disturb occurs.
                "
            
            ::= { hwAtmCesPortCfgEntry 14 }
        
        -- 1.3.6.1.4.1.2011.5.11.3.1.15
        hwAtmCesPortCfgESAlarmThreshold OBJECT-TYPE
            SYNTAX     Integer32 (1..3600)
            MAX-ACCESS read-write
            STATUS     current
            DESCRIPTION
                "Errored seconds alarm threshold."
            ::= { hwAtmCesPortCfgEntry 15 }
        
        -- 1.3.6.1.4.1.2011.5.11.3.1.16
        hwAtmCesPortCfgCSESAlarmThreshold OBJECT-TYPE
            SYNTAX     Integer32 (1..60)
            MAX-ACCESS read-write
            STATUS     current
            DESCRIPTION
                "Consecutive severely errored seconds alarm threshold."
            ::= { hwAtmCesPortCfgEntry 16 }
        
        -- 1.3.6.1.4.1.2011.5.11.3.1.17
        hwAtmCesPortCfgDMAlarmThreshold OBJECT-TYPE
            SYNTAX     Integer32 (1..60)
            MAX-ACCESS read-write
            STATUS     current
            DESCRIPTION
                "Degraded minutes alarm threshold."
            ::= { hwAtmCesPortCfgEntry 17 }
        
        -- 1.3.6.1.4.1.2011.5.11.3.1.18
        hwAtmCesPortLineCode OBJECT-TYPE
            SYNTAX     INTEGER
                {
                hdb3(1),
                ami(2),
                b8zs(3),
                invalidCode(-1)
                }
            MAX-ACCESS read-write
            STATUS     current
            DESCRIPTION
                "Configuration of the line encoding type.
                 Options:
                 1. hdb3(1)        - HDB3 code
                 2. ami(2)         - AMI code
                 3. b8zs(3)        - B8ZS code
                 4. invalidCode(-1) - Invalid code
                "
            ::= { hwAtmCesPortCfgEntry 18 }
        
        -- 1.3.6.1.4.1.2011.5.11.3.1.19
        hwAtmCesPortAcmSource OBJECT-TYPE
            SYNTAX     Integer32
            MAX-ACCESS read-write
            STATUS     current
            DESCRIPTION
                "Configuration of adaptive clock source."
            ::= { hwAtmCesPortCfgEntry 19 }
            
        -- 1.3.6.1.4.1.2011.5.11.3.1.20
        hwAtmCesPortCfgState OBJECT-TYPE
            SYNTAX     INTEGER
                {
                notConfigUserType(1),
                configVoiceUserType(2),
                configPWUserType(3),
                configNativeTDM(4)
                }
            MAX-ACCESS read-only
            STATUS     current
            DESCRIPTION
                "Indicates the configuration status of the subscriber type.
                 Options:
                 1. notConfigUserType(1)   - Did not configure
                 2. configVoiceUserType(2) - Configured MG PRA subscriber
                 3. configPWUserType(3)    - Configured Connection user
                 4. configNativeTDM(4)     - Configured Native TDM
                "
            ::= { hwAtmCesPortCfgEntry 20 }         
        
        -- 1.3.6.1.4.1.2011.5.11.4
        hwAtmCesPortV35CfgTable OBJECT-TYPE
            SYNTAX SEQUENCE OF HwAtmCesPortV35CfgEntry
            MAX-ACCESS not-accessible
            STATUS     current
            DESCRIPTION
                "Port configration table of V35.
                 This table is used to configure the CES-V35 port. The configuration includes reversing the clock and clock mode, blocking and unblocking the port, and querying the N value, status and alarm of the port.     
                 The index of this table is ifIndex. 
                "
            ::= { hwCes 4 }
        
        -- 1.3.6.1.4.1.2011.5.11.4.1
        hwAtmCesPortV35CfgEntry OBJECT-TYPE
            SYNTAX HwAtmCesPortV35CfgEntry
            MAX-ACCESS not-accessible
            STATUS     current
            DESCRIPTION          
                "Port configration table of V35.
                 This table is used to configure the CES-V35 port. The configuration includes reversing the clock and clock mode, blocking and unblocking the port, and querying the N value, status and alarm of the port.     
                 The index of this entry is ifIndex.
                "
            INDEX { ifIndex }
            ::= { hwAtmCesPortV35CfgTable 1 }
        
        HwAtmCesPortV35CfgEntry ::=
            SEQUENCE { 
                hwAtmCesPortV35CfgNValue
                    Integer32,
                hwAtmCesPortV35CfgClockMode
                    INTEGER,
                hwAtmCesPortV35CfgBlockStatus
                    INTEGER,
                hwAtmCesPortV35CfgReversePhase
                    INTEGER,
                hwAtmCesPortV35CfgWarningStatus
                    Integer32,
                hwAtmCesPortV35CfgPortV35Status
                    INTEGER
             }

        -- 1.3.6.1.4.1.2011.5.11.4.1.1
        hwAtmCesPortV35CfgNValue OBJECT-TYPE
            SYNTAX     Integer32 (1..32)
            MAX-ACCESS read-only
            STATUS     current
            DESCRIPTION
                "N value of V35 port."
            ::= { hwAtmCesPortV35CfgEntry 1 }
        
        -- 1.3.6.1.4.1.2011.5.11.4.1.2
        hwAtmCesPortV35CfgClockMode OBJECT-TYPE
            SYNTAX     INTEGER
                {
                dceInternal(1),
                dceSlave(2),
                dceExternal(3),
                dteInternal(4),
                dteSlave(5),
                dteExternal(6)
                }
            MAX-ACCESS read-write
            STATUS     current
            DESCRIPTION
                "Clock mode of port.
                 Options:
                 1. dceInternal(1) - Dec-Internal clock
                 2. dceSlave(2)    - Dec-Slave clock
                 3. dceExternal(3) - Dec-External clock
                 4. dteInternal(4) - Dte-Internal clock
                 5. dteSlave(5)    - Dte-Slave clock
                 6. dteExternal(6) - Dte-External clock
                "
            ::= { hwAtmCesPortV35CfgEntry 2 }
        
        -- 1.3.6.1.4.1.2011.5.11.4.1.3
        hwAtmCesPortV35CfgBlockStatus OBJECT-TYPE
            SYNTAX     INTEGER
                {
                block(1),
                unblock(2),
                invalidStatus(-1)
                }
            MAX-ACCESS read-write
            STATUS     current
            DESCRIPTION
                "To block or unblock the port, or to inquiry the block state.
                 Options:
                 1. block(1)          - Block the port
                 2. unblock(2)        - UnBlock the port
                 3. invalidStatus(-1) - Invalid status
                "
            ::= { hwAtmCesPortV35CfgEntry 3 }
        
        -- 1.3.6.1.4.1.2011.5.11.4.1.4
        hwAtmCesPortV35CfgReversePhase OBJECT-TYPE
            SYNTAX     INTEGER
                {
                noInverse(1),
                inverse(2)
                }
            MAX-ACCESS read-write
            STATUS     current
            DESCRIPTION
                "Inverse the clock of V35 port, inquiry the clock state.
                 Options:
                 1. noInverse(1) - Not inverse state
                 2. inverse(2)   - Inverse state
                "
            ::= { hwAtmCesPortV35CfgEntry 4 }
        
        -- 1.3.6.1.4.1.2011.5.11.4.1.5
        hwAtmCesPortV35CfgWarningStatus OBJECT-TYPE
            SYNTAX     Integer32 (0..127)
            MAX-ACCESS read-only
            STATUS     current
            DESCRIPTION
                "Alarm state of V35 port."
            ::= { hwAtmCesPortV35CfgEntry 5 }
        
        -- 1.3.6.1.4.1.2011.5.11.4.1.6
        hwAtmCesPortV35CfgPortV35Status OBJECT-TYPE
            SYNTAX     INTEGER
                {
                idle(1),
                normal(2),
                localLoop(3),
                remoteLoop(4),
                block(5),
                fault(6)
                }
            MAX-ACCESS read-only
            STATUS     current
            DESCRIPTION
                "Port state of V35.
                 Options:
                 1. idle(1)       - Idle state
                 2. normal(2)     - Normal state
                 3. localLoop(3)  - Local loop state
                 4. remoteLoop(4) - Remote loop state
                 5. block(5)      - Block state
                 6. fault(6)      - Fault state
                "
            ::= { hwAtmCesPortV35CfgEntry 6 }
        
        -- 1.3.6.1.4.1.2011.5.11.5
        hwAtmCesChnlStatisTable OBJECT-TYPE
            SYNTAX SEQUENCE OF HwAtmCesChnlStatisEntry
            MAX-ACCESS not-accessible
            STATUS     current
            DESCRIPTION
                "The statistics table of CES channel. This table is used to 
                 collect the cell data of the SDT port.  
                 The index of this table is ifIndex. 
                "
            ::= { hwCes 5 }
        
        -- 1.3.6.1.4.1.2011.5.11.5.1
        hwAtmCesChnlStatisEntry OBJECT-TYPE
            SYNTAX HwAtmCesChnlStatisEntry
            MAX-ACCESS not-accessible
            STATUS     current
            DESCRIPTION          
                "The statistics table of CES channel. This table is used to 
                 collect the cell data of the SDT port.  
                 The index of this entry is ifIndex.
                "
            INDEX { ifIndex }
            ::= { hwAtmCesChnlStatisTable 1 }
        
        HwAtmCesChnlStatisEntry ::=
            SEQUENCE 
                { 
                hwAtmCesChnlStatisCounter0
                    Counter32,
                hwAtmCesChnlStatisCounter1
                    Counter32,
                hwAtmCesChnlStatisCounter2
                    Counter32,
                hwAtmCesChnlStatisCounter3
                    Counter32,
                hwAtmCesChnlStatisCounter4
                    Counter32,
                hwAtmCesChnlStatisCounter5
                    Counter32,
                hwAtmCesChnlStatisCounter6
                    Counter32,
                hwAtmCesChnlStatisCounter7
                    Counter32,
                hwAtmCesChnlStatisCounter8
                    Counter32,
                hwAtmCesChnlStatisCounter9
                    Counter32,
                hwAtmCesChnlStatisCounter10
                    Counter32,
                hwAtmCesChnlStatisCounter11
                    Counter32,
                hwAtmCesChnlStatisCounter12
                    Counter32,
                hwAtmCesChnlStatisCounter13
                    Counter32,
                hwAtmCesChnlStatisCounter14
                    Counter32,
                hwAtmCesChnlStatisCounter15
                    Counter32,
                hwAtmCesChnlStatisOper
                    INTEGER
                }

        -- 1.3.6.1.4.1.2011.5.11.5.1.1
        hwAtmCesChnlStatisCounter0 OBJECT-TYPE
            SYNTAX     Counter32
            MAX-ACCESS read-only
            STATUS     current
            DESCRIPTION
                "Number of discarded cells due to Output Queue or Segmentation Buffer."
            ::= { hwAtmCesChnlStatisEntry 1 }
        
        -- 1.3.6.1.4.1.2011.5.11.5.1.2
        hwAtmCesChnlStatisCounter1 OBJECT-TYPE
            SYNTAX     Counter32
            MAX-ACCESS read-only
            STATUS     current
            DESCRIPTION
                "Not used."
            ::= { hwAtmCesChnlStatisEntry 2 }
        
        -- 1.3.6.1.4.1.2011.5.11.5.1.3
        hwAtmCesChnlStatisCounter2 OBJECT-TYPE
            SYNTAX     Counter32
            MAX-ACCESS read-only
            STATUS     current
            DESCRIPTION
                "Number of cells written to the Reassembly Buffer. It excludes cells that were discarded for any 
                 reason and cells that are inserted instead of lost cells (atmfReassembledCells).
                "
            ::= { hwAtmCesChnlStatisEntry 3 }
        
        -- 1.3.6.1.4.1.2011.5.11.5.1.4
        hwAtmCesChnlStatisCounter3 OBJECT-TYPE
            SYNTAX     Counter32
            MAX-ACCESS read-only
            STATUS     current
            DESCRIPTION
                "Number of times incomingMFB pulse is not synchronous to SDT start of structure upstream (AAL1)."
            ::= { hwAtmCesChnlStatisEntry 4 }
        
        -- 1.3.6.1.4.1.2011.5.11.5.1.5
        hwAtmCesChnlStatisCounter4 OBJECT-TYPE
            SYNTAX     Counter32
            MAX-ACCESS read-only
            STATUS     current
            DESCRIPTION
                "Number of cells causing a Reassembly Buffer overflow (AAL0 & AAL1). It includes accepted cells 
                 that are causing the filling level to exceed the predefined threshold and discarded cells due to 
                 the attempt of writing to the Reassembly Buffer when the threshold is already exceeded.
                "
            ::= { hwAtmCesChnlStatisEntry 5 }
        
        -- 1.3.6.1.4.1.2011.5.11.5.1.6
        hwAtmCesChnlStatisCounter5 OBJECT-TYPE
            SYNTAX     Counter32
            MAX-ACCESS read-only
            STATUS     current
            DESCRIPTION
                "Number of end of Reassembly Buffer overflow (AAL0 & AAL1). The value is incremented upon acceptance 
                 of the next cell after Reassembly Buffer overflow.
                "
            ::= { hwAtmCesChnlStatisEntry 6 }
        
        -- 1.3.6.1.4.1.2011.5.11.5.1.7
        hwAtmCesChnlStatisCounter6 OBJECT-TYPE
            SYNTAX     Counter32
            MAX-ACCESS read-only
            STATUS     current
            DESCRIPTION
                "The count of the number of AAL1 header errors detected including those corrected. Header errors include 
                 correctable and uncorrectable CRC, plus bad parity. (atmfCESHdrErrors).
                "
            ::= { hwAtmCesChnlStatisEntry 7 }
        
        -- 1.3.6.1.4.1.2011.5.11.5.1.8
        hwAtmCesChnlStatisCounter7 OBJECT-TYPE
            SYNTAX     Counter32
            MAX-ACCESS read-only
            STATUS     current
            DESCRIPTION
                "Number of times that the sequence number of an 
                 incoming AAL1 SARPDU causes a transition of the
                 SC algorithm from 'sync' to 'out of sequence' and 
                 from 'invalid' to 'out of sync'.
                "
            ::= { hwAtmCesChnlStatisEntry 8 }
        
        -- 1.3.6.1.4.1.2011.5.11.5.1.9
        hwAtmCesChnlStatisCounter8 OBJECT-TYPE
            SYNTAX     Counter32
            MAX-ACCESS read-only
            STATUS     current
            DESCRIPTION
                "Number of downstream 'misinserted cells' detected by the AAL1 sequence count 
                 algorithm (atmfCESMisinsertedCells).
                "
            ::= { hwAtmCesChnlStatisEntry 9 }
        
        -- 1.3.6.1.4.1.2011.5.11.5.1.10
        hwAtmCesChnlStatisCounter9 OBJECT-TYPE
            SYNTAX     Counter32
            MAX-ACCESS read-only
            STATUS     current
            DESCRIPTION
                "Number of downstream cells discarded by the AAL1 sequence count algorithm."
            ::= { hwAtmCesChnlStatisEntry 10 }
        
        -- 1.3.6.1.4.1.2011.5.11.5.1.11
        hwAtmCesChnlStatisCounter10 OBJECT-TYPE
            SYNTAX     Counter32
            MAX-ACCESS read-only
            STATUS     current
            DESCRIPTION
                "Number of rejected AAL1 SDT pointers due to parity error or wrong pointer value (93 < pointer <127)."
            ::= { hwAtmCesChnlStatisEntry 11 }
        
        -- 1.3.6.1.4.1.2011.5.11.5.1.12
        hwAtmCesChnlStatisCounter11 OBJECT-TYPE
            SYNTAX     Counter32
            MAX-ACCESS read-only
            STATUS     current
            DESCRIPTION
                "Number of SC cycles with more than one AAL1 SDT pointer field if only one pointer is expected (sdt_once = 1)."
            ::= { hwAtmCesChnlStatisEntry 12 }
        
        -- 1.3.6.1.4.1.2011.5.11.5.1.13
        hwAtmCesChnlStatisCounter12 OBJECT-TYPE
            SYNTAX     Counter32
            MAX-ACCESS read-only
            STATUS     current
            DESCRIPTION
                "Number of start of reassembly buffer underflow (AAL0 & AAL1) (atmfCESBufUnderflow)."
            ::= { hwAtmCesChnlStatisEntry 13 }
        
        -- 1.3.6.1.4.1.2011.5.11.5.1.14
        hwAtmCesChnlStatisCounter13 OBJECT-TYPE
            SYNTAX     Counter32
            MAX-ACCESS read-only
            STATUS     current
            DESCRIPTION
                "Number of inserted starvation cells (AAL0 & AAL1) due to reassembly buffer underflow."
            ::= { hwAtmCesChnlStatisEntry 14 }
        
        -- 1.3.6.1.4.1.2011.5.11.5.1.15
        hwAtmCesChnlStatisCounter14 OBJECT-TYPE
            SYNTAX     Counter32
            MAX-ACCESS read-only
            STATUS     current
            DESCRIPTION
                "Number of times the Reassembly Buffer is re-initialized due to AAL1 start of structure 
                 is out of sync with port start of structure.This records the count of the number of events 
                 in which the AAL1 reassembler found that an SDT pointer is not where it is expected, and the 
                 pointer must be reacquired. This count is only meaningful for structured CES. (atmfCESPointerReframes).
                "
            ::= { hwAtmCesChnlStatisEntry 15 }
        
        -- 1.3.6.1.4.1.2011.5.11.5.1.16
        hwAtmCesChnlStatisCounter15 OBJECT-TYPE
            SYNTAX     Counter32
            MAX-ACCESS read-only
            STATUS     current
            DESCRIPTION
                "Number of downstream 'Lost cells' detected by the AAL1 sequence count algorithm (atmfCESLostCells)."
            ::= { hwAtmCesChnlStatisEntry 16 }
        
        -- 1.3.6.1.4.1.2011.5.11.5.1.17
        hwAtmCesChnlStatisOper OBJECT-TYPE
            SYNTAX INTEGER { clear(1) }
            MAX-ACCESS read-write
            STATUS     current
            DESCRIPTION
                "The operating code of clearing the statistics of CES SDT port.
                 Options:
                 1. clear(1) - Clear the statistics of CES SDT port
                "
            ::= { hwAtmCesChnlStatisEntry 17 }
               
        -- 1.3.6.1.4.1.2011.5.11.6
        hwAtmCesUDTPortStatisTable OBJECT-TYPE
            SYNTAX SEQUENCE OF HwAtmCesUDTPortStatisEntry
            MAX-ACCESS not-accessible
            STATUS     current
            DESCRIPTION
                "The statistics table of CES UDT port.
                 This table is used to collect the cell data of the UDT port.   
                 The index of this table is ifIndex.
                "
            ::= { hwCes 6 }
              
        -- 1.3.6.1.4.1.2011.5.11.6.1
        hwAtmCesUDTPortStatisEntry OBJECT-TYPE
            SYNTAX HwAtmCesUDTPortStatisEntry
            MAX-ACCESS not-accessible
            STATUS current
            DESCRIPTION          
                "The statistics table of CES UDT port.
                 This table is used to collect the cell data of the UDT port.   
                 The index of this entry is ifIndex.
                "
            INDEX { ifIndex }
            ::= { hwAtmCesUDTPortStatisTable 1 }
             
        HwAtmCesUDTPortStatisEntry ::=
            SEQUENCE 
                { 
                hwAtmCesUDTPortStatisCounter0
                    Counter32,
                hwAtmCesUDTPortStatisCounter1
                    Counter32,
                hwAtmCesUDTPortStatisCounter2
                    Counter32,
                hwAtmCesUDTPortStatisCounter3
                    Counter32,
                hwAtmCesUDTPortStatisCounter4
                    Counter32,
                hwAtmCesUDTPortStatisCounter5
                    Counter32,
                hwAtmCesUDTPortStatisCounter6
                    Counter32,
                hwAtmCesUDTPortStatisCounter7
                    Counter32,
                hwAtmCesUDTPortStatisCounter8
                    Counter32,
                hwAtmCesUDTPortStatisCounter9
                    Counter32,
                hwAtmCesUDTPortStatisCounter10
                    Counter32,
                hwAtmCesUDTPortStatisCounter11
                    Counter32,
                hwAtmCesUDTPortStatisCounter12
                    Counter32,
                hwAtmCesUDTPortStatisCounter13
                    Counter32,
                hwAtmCesUDTPortStatisCounter14
                    Counter32,
                hwAtmCesUDTPortStatisCounter15
                    Counter32,
                hwAtmCesUDTPortStatisOper
                    INTEGER
                }

        -- 1.3.6.1.4.1.2011.5.11.6.1.1
        hwAtmCesUDTPortStatisCounter0 OBJECT-TYPE
            SYNTAX     Counter32
            MAX-ACCESS read-only
            STATUS     current
            DESCRIPTION
                "Number of discarded cells due to Output Queue or Segmentation Buffer."
            ::= { hwAtmCesUDTPortStatisEntry 1 }
        
        -- 1.3.6.1.4.1.2011.5.11.6.1.2
        hwAtmCesUDTPortStatisCounter1 OBJECT-TYPE
            SYNTAX     Counter32
            MAX-ACCESS read-only
            STATUS     current
            DESCRIPTION
                "Not used."
            ::= { hwAtmCesUDTPortStatisEntry 2 }
        
        -- 1.3.6.1.4.1.2011.5.11.6.1.3
        hwAtmCesUDTPortStatisCounter2 OBJECT-TYPE
            SYNTAX     Counter32
            MAX-ACCESS read-only
            STATUS     current
            DESCRIPTION
                "Number of cells written to the Reassembly Buffer. It excludes cells that were discarded 
                 for any reason and cells that are inserted instead of lost cells (atmfReassembledCells).
                "
            ::= { hwAtmCesUDTPortStatisEntry 3 }
        
        -- 1.3.6.1.4.1.2011.5.11.6.1.4
        hwAtmCesUDTPortStatisCounter3 OBJECT-TYPE
            SYNTAX     Counter32
            MAX-ACCESS read-only
            STATUS     current
            DESCRIPTION
                "Number of times incomingMFB pulse is not synchronous to SDT start of structure upstream (AAL1)."
            ::= { hwAtmCesUDTPortStatisEntry 4 }
        
        -- 1.3.6.1.4.1.2011.5.11.6.1.5
        hwAtmCesUDTPortStatisCounter4 OBJECT-TYPE
            SYNTAX     Counter32
            MAX-ACCESS read-only
            STATUS     current
            DESCRIPTION
                "Number of cells causing a Reassembly Buffer overflow (AAL0 & AAL1). It includes accepted cells 
                 that are causing the filling level to exceed the predefined threshold and discarded cells due to 
                 the attempt of writing to the Reassembly Buffer when the threshold is already exceeded.
                "
            ::= { hwAtmCesUDTPortStatisEntry 5 }
        
        -- 1.3.6.1.4.1.2011.5.11.6.1.6
        hwAtmCesUDTPortStatisCounter5 OBJECT-TYPE
            SYNTAX     Counter32
            MAX-ACCESS read-only
            STATUS     current
            DESCRIPTION
                "Number of end of Reassembly Buffer overflow (AAL0 & AAL1). The value is incremented upon acceptance 
                 of the next cell after Reassembly Buffer overflow.
                "
            ::= { hwAtmCesUDTPortStatisEntry 6 }
        
        -- 1.3.6.1.4.1.2011.5.11.6.1.7
        hwAtmCesUDTPortStatisCounter6 OBJECT-TYPE
            SYNTAX     Counter32
            MAX-ACCESS read-only
            STATUS     current
            DESCRIPTION
                "The count of the number of AAL1 header errors detected including those corrected. Header errors include
                 correctable and uncorrectable CRC, plus bad parity. (atmfCESHdrErrors).
                "
            ::= { hwAtmCesUDTPortStatisEntry 7 }
        
        -- 1.3.6.1.4.1.2011.5.11.6.1.8
        hwAtmCesUDTPortStatisCounter7 OBJECT-TYPE
            SYNTAX     Counter32
            MAX-ACCESS read-only
            STATUS     current
            DESCRIPTION
                "Number of times that the sequence number of 
                 an incoming AAL1 SARPDU causes a transition of 
                 the SC algorithm from 'sync' to 'out of sequence' 
                 and from 'invalid' to 'out of sync'.
                "
            ::= { hwAtmCesUDTPortStatisEntry 8 }
        
        -- 1.3.6.1.4.1.2011.5.11.6.1.9
        hwAtmCesUDTPortStatisCounter8 OBJECT-TYPE
            SYNTAX     Counter32
            MAX-ACCESS read-only
            STATUS     current
            DESCRIPTION
                "Number of downstream 'misinserted cells' detected by the AAL1 sequence count algorithm (atmfCESMisinsertedCells)."
            ::= { hwAtmCesUDTPortStatisEntry 9 }
        
        -- 1.3.6.1.4.1.2011.5.11.6.1.10
        hwAtmCesUDTPortStatisCounter9 OBJECT-TYPE
            SYNTAX Counter32
            MAX-ACCESS read-only
            STATUS current
            DESCRIPTION
                "Number of downstream cells discarded by the AAL1 sequence count algorithm."
            ::= { hwAtmCesUDTPortStatisEntry 10 }
        
        -- 1.3.6.1.4.1.2011.5.11.6.1.11
        hwAtmCesUDTPortStatisCounter10 OBJECT-TYPE
            SYNTAX     Counter32
            MAX-ACCESS read-only
            STATUS     current
            DESCRIPTION
                "Number of rejected AAL1 SDT pointers due to parity error or wrong pointer value (93 < pointer <127)."
            ::= { hwAtmCesUDTPortStatisEntry 11 }
        
        -- 1.3.6.1.4.1.2011.5.11.6.1.12
        hwAtmCesUDTPortStatisCounter11 OBJECT-TYPE
            SYNTAX Counter32
            MAX-ACCESS read-only
            STATUS current
            DESCRIPTION
                "Number of SC cycles with more than one AAL1 SDT pointer field if only one pointer is expected (sdt_once = 1)."
            ::= { hwAtmCesUDTPortStatisEntry 12 }
        
        -- 1.3.6.1.4.1.2011.5.11.6.1.13
        hwAtmCesUDTPortStatisCounter12 OBJECT-TYPE
            SYNTAX     Counter32
            MAX-ACCESS read-only
            STATUS     current
            DESCRIPTION
                "Number of start of reassembly buffer underflow (AAL0 & AAL1) (atmfCESBufUnderflow)."
            ::= { hwAtmCesUDTPortStatisEntry 13 }
        
        -- 1.3.6.1.4.1.2011.5.11.6.1.14
        hwAtmCesUDTPortStatisCounter13 OBJECT-TYPE
            SYNTAX     Counter32
            MAX-ACCESS read-only
            STATUS     current
            DESCRIPTION
                "Number of inserted starvation cells (AAL0 & AAL1) due to reassembly buffer underflow."
            ::= { hwAtmCesUDTPortStatisEntry 14 }
        
        -- 1.3.6.1.4.1.2011.5.11.6.1.15
        hwAtmCesUDTPortStatisCounter14 OBJECT-TYPE
            SYNTAX     Counter32
            MAX-ACCESS read-only
            STATUS     current
            DESCRIPTION
                "Number of times the Reassembly Buffer is re-initialized due to AAL1 start of structure is out of 
                 sync with port start of structure.This records the count of the number of events in which the AAL1 
                 reassembler found that an SDT pointer is not where it is expected, and the pointer must be reacquired. 
                 This count is only meaningful for structured CES. (atmfCESPointerReframes).
                "
            ::= { hwAtmCesUDTPortStatisEntry 15 }
        
        -- 1.3.6.1.4.1.2011.5.11.6.1.16
        hwAtmCesUDTPortStatisCounter15 OBJECT-TYPE
            SYNTAX     Counter32
            MAX-ACCESS read-only
            STATUS     current
            DESCRIPTION
                "Number of downstream 'lost cells' detected by the AAL1 sequence count algorithm (atmfCESLostCells)."
            ::= { hwAtmCesUDTPortStatisEntry 16 }
        
        -- 1.3.6.1.4.1.2011.5.11.6.1.17
        hwAtmCesUDTPortStatisOper OBJECT-TYPE
            SYNTAX     INTEGER { clear(1) }
            MAX-ACCESS read-write
            STATUS     current
            DESCRIPTION
                "The operating code of clearing the statistics of CES UDT port.
                 Options:
                 1. clear(1) - Clear the statistics of CES UDT port
                "
            ::= { hwAtmCesUDTPortStatisEntry 17 }
        
        -- 1.3.6.1.4.1.2011.5.11.7
        hwAtmCesUNIPortStatisTable OBJECT-TYPE
            SYNTAX SEQUENCE OF HwAtmCesUNIPortStatisEntry
            MAX-ACCESS not-accessible
            STATUS     current
            DESCRIPTION
                "The statistics table of CES UNI port.
                 This table is used to collect the cell data of the UNI port.
                 The index of this table is ifIndex.
                "
            ::= { hwCes 7 }
        
        -- 1.3.6.1.4.1.2011.5.11.7.1
        hwAtmCesUNIPortStatisEntry OBJECT-TYPE
            SYNTAX HwAtmCesUNIPortStatisEntry
            MAX-ACCESS not-accessible
            STATUS     current
            DESCRIPTION          
                "The statistics table of CES UNI port.
                 This table is used to collect the cell data of the UNI port.   
                 The index of this entry is ifIndex.
                "
            INDEX { ifIndex }
            ::= { hwAtmCesUNIPortStatisTable 1 }
        
        HwAtmCesUNIPortStatisEntry ::=
            SEQUENCE 
                { 
                hwAtmCesUNIPortStatisCounter0
                    Counter32,
                hwAtmCesUNIPortStatisCounter1
                    Counter32,
                hwAtmCesUNIPortStatisCounter2
                    Counter32,
                hwAtmCesUNIPortStatisCounter3
                    Counter32,
                hwAtmCesUNIPortStatisCounter4
                    Counter32,
                hwAtmCesUNIPortStatisOper
                    INTEGER
                }

        -- 1.3.6.1.4.1.2011.5.11.7.1.1
        hwAtmCesUNIPortStatisCounter0 OBJECT-TYPE
            SYNTAX     Counter32
            MAX-ACCESS read-only
            STATUS     current
            DESCRIPTION
                "Number of discarded cells due to output queue, ATM Receive Buffer."
            ::= { hwAtmCesUNIPortStatisEntry 1 }
        
        -- 1.3.6.1.4.1.2011.5.11.7.1.2
        hwAtmCesUNIPortStatisCounter1 OBJECT-TYPE
            SYNTAX     Counter32
            MAX-ACCESS read-only
            STATUS     current
            DESCRIPTION
                "Number of received cells with corrected HEC errors."
            ::= { hwAtmCesUNIPortStatisEntry 2 }
        
        -- 1.3.6.1.4.1.2011.5.11.7.1.3
        hwAtmCesUNIPortStatisCounter2 OBJECT-TYPE
            SYNTAX     Counter32
            MAX-ACCESS read-only
            STATUS     current
            DESCRIPTION
                "Number of received cells with non-corrected HEC errors."
            ::= { hwAtmCesUNIPortStatisEntry 3 }
        
        -- 1.3.6.1.4.1.2011.5.11.7.1.4
        hwAtmCesUNIPortStatisCounter3 OBJECT-TYPE
            SYNTAX     Counter32
            MAX-ACCESS read-only
            STATUS     current
            DESCRIPTION
                "Number of times cell delineation SYNC state is left, except when forced."
            ::= { hwAtmCesUNIPortStatisEntry 4 }
        
        -- 1.3.6.1.4.1.2011.5.11.7.1.5
        hwAtmCesUNIPortStatisCounter4 OBJECT-TYPE
            SYNTAX     Counter32
            MAX-ACCESS read-only
            STATUS     current
            DESCRIPTION
                "Number of discarded cells due to ATM transmit buffer overflow."
            ::= { hwAtmCesUNIPortStatisEntry 5 }
        
        -- 1.3.6.1.4.1.2011.5.11.7.1.6
        hwAtmCesUNIPortStatisOper OBJECT-TYPE
            SYNTAX     INTEGER { clear(1) }
            MAX-ACCESS read-write
            STATUS     current
            DESCRIPTION
                "The operating code of clearing the statistics of CES UNI port.
                 Options:
                 1. clear(1) - Clear the statistics of CES UNI port
                "
            ::= { hwAtmCesUNIPortStatisEntry 6 }
        
        -- 1.3.6.1.4.1.2011.5.11.8
        hwAtmCesPortMaintTable OBJECT-TYPE
            SYNTAX SEQUENCE OF HwAtmCesPortMaintEntry
            MAX-ACCESS not-accessible
            STATUS     current
            DESCRIPTION
                "The maintenace table of CES port.
                 This table is used to set the loopback of the CES port, including the local loopback (LL), remote loopback (RL), and timeslot loopback.      
                 The timeslot loopback takes effect only on the CES-SDT port.  
                 The index of this table is ifIndex.
                "
            ::= { hwCes 8 }
        
        -- 1.3.6.1.4.1.2011.5.11.8.1
        hwAtmCesPortMaintEntry OBJECT-TYPE
            SYNTAX HwAtmCesPortMaintEntry
            MAX-ACCESS not-accessible
            STATUS     current
            DESCRIPTION          
                "The maintenace table of CES port.
                 This table is used to set the loopback of the CES port, including the local loopback (LL), remote loopback (RL), and timeslot loopback.      
                 The timeslot loopback takes effect only on the CES-SDT port.  
                 The index of this entry is ifIndex.
                "
            INDEX { ifIndex }
            ::= { hwAtmCesPortMaintTable 1 }
        
        HwAtmCesPortMaintEntry ::=
            SEQUENCE 
                { 
                hwAtmCesPortMaintLoop
                    INTEGER,
                hwAtmCesPortMaintOper
                    INTEGER,
                hwAtmCesPortMaintSingleTimeslotId
                    Integer32
                }

        -- 1.3.6.1.4.1.2011.5.11.8.1.1
        hwAtmCesPortMaintLoop OBJECT-TYPE
            SYNTAX INTEGER
                {
                noLoop(1),
                localLoop(2),
                remoteLoop(3),
                tsLocalLoop(4),
                payLoadLoop(5)
                }
            MAX-ACCESS read-write
            STATUS current
            DESCRIPTION
                "The looping test mode of CES port.
                 Options:
                 1. noLoop(1)      - No-loop test
                 2. localLoop(2)   - Local-loop test
                 3. remoteLoop(3)  - Remote-loop test
                 4. tsLocalLoop(4) - Ts-Localloop test
                 5. payLoadLoop(5) - Payload-loop test
                "
            ::= { hwAtmCesPortMaintEntry 1 }
        
        -- 1.3.6.1.4.1.2011.5.11.8.1.2
        hwAtmCesPortMaintOper OBJECT-TYPE
            SYNTAX INTEGER
                {
                set(1),
                clear(2),
                notSupportQuery(-1)
                }
            MAX-ACCESS read-write
            STATUS current
            DESCRIPTION
                "The oprating of looping test mode.
                 Options:
                 1. set(1)              - Set looping test
                 2. clear(2)            - Clear looping test
                 3. notSupportQuery(-1) - Not support query
                "
            ::= { hwAtmCesPortMaintEntry 2 }
        
        -- 1.3.6.1.4.1.2011.5.11.8.1.3
        hwAtmCesPortMaintSingleTimeslotId OBJECT-TYPE
            SYNTAX Integer32 (0..31)
            MAX-ACCESS read-write
            STATUS current
            DESCRIPTION
                "The timeslot number of single timeslot looping test."
            ::= { hwAtmCesPortMaintEntry 3 }
        
--E1 monitor status control table
        -- 1.3.6.1.4.1.2011.5.11.11
        hwCesECSMonitorControlTable OBJECT-TYPE
            SYNTAX SEQUENCE OF HwCesECSMonitorControlEntry
            MAX-ACCESS not-accessible
            STATUS current
            DESCRIPTION
                "E1 monitor status control table.
                 The indexes of this table are ifIndex and hwCesECSMonitorPeriodType.
                "
            ::= { hwCes 11 }
        
        -- 1.3.6.1.4.1.2011.5.11.11.1
        hwCesECSMonitorControlEntry OBJECT-TYPE
            SYNTAX HwCesECSMonitorControlEntry
            MAX-ACCESS not-accessible
            STATUS current
            DESCRIPTION
                "E1 monitor status control table.
                 The indexes of this entry are ifIndex and hwCesECSMonitorPeriodType.
                "
            INDEX { ifIndex, hwCesECSMonitorPeriodType }
            ::= { hwCesECSMonitorControlTable 1 }
        
        HwCesECSMonitorControlEntry ::=
            SEQUENCE { 
                hwCesECSMonitorPeriodType
                    INTEGER,
                hwCesECSMonitorStatusReal
                    INTEGER,
                hwCesECSMonitorStartTimeReal
                    DateAndTime,
                hwCesECSMonitorStatusUserSet
                    INTEGER,
                hwCesECSMonitorStartTimeUserSet
                    DateAndTime
             }

        -- 1.3.6.1.4.1.2011.5.11.11.1.1
        hwCesECSMonitorPeriodType OBJECT-TYPE
        
            SYNTAX INTEGER
                {
                quarter(1),
                day(2)
                }
            MAX-ACCESS read-write
            STATUS current
            DESCRIPTION
                "Monitor period type.
                 Options:
                 1. quarter(1) - Quarter
                 2. day(2)     - Day
                "
            ::= { hwCesECSMonitorControlEntry 1 }
        
        -- 1.3.6.1.4.1.2011.5.11.11.1.2
        hwCesECSMonitorStatusReal OBJECT-TYPE
            SYNTAX INTEGER
                {
                disable(0),
                enable(1)
                }
            MAX-ACCESS read-only
            STATUS current
            DESCRIPTION
                "Current monitor status, 0:disable, 1:enable.
                 Options:
                 1. disable(0) - Disable current monitor
                 2. enable(1)  - Enable current monitor
                "
            ::= { hwCesECSMonitorControlEntry 2 }
        
        -- 1.3.6.1.4.1.2011.5.11.11.1.3
        hwCesECSMonitorStartTimeReal OBJECT-TYPE
            SYNTAX DateAndTime
            MAX-ACCESS read-only
            STATUS current
            DESCRIPTION
                "The start time of the monitor."
            ::= { hwCesECSMonitorControlEntry 3 }
        
        -- 1.3.6.1.4.1.2011.5.11.11.1.4
        hwCesECSMonitorStatusUserSet OBJECT-TYPE
            SYNTAX INTEGER
                {
                disable(0),
                enable(1)
                }
            MAX-ACCESS read-write
            STATUS current
            DESCRIPTION
                "The monitor status set by user.
                 Options:
                 1. disable(0) - Set monitor close
                 2. enable(1)  - Set monitor open
                "
            ::= { hwCesECSMonitorControlEntry 4 }
        
        -- 1.3.6.1.4.1.2011.5.11.11.1.5
        hwCesECSMonitorStartTimeUserSet OBJECT-TYPE
            SYNTAX DateAndTime
            MAX-ACCESS read-write
            STATUS current
            DESCRIPTION
                "The start time of the monitor set by user."
            ::= { hwCesECSMonitorControlEntry 5 }
        
--E1 threshold enable table
        -- 1.3.6.1.4.1.2011.5.11.12
        hwCesECSThresholdControlTable OBJECT-TYPE
            SYNTAX SEQUENCE OF HwCesECSThresholdControlEntry
            MAX-ACCESS not-accessible
            STATUS current
            DESCRIPTION
                "E1 threshold enable table.
                 The indexes of this table are ifIndex and hwCesECSMonitorPeriodType.
                "
            ::= { hwCes 12 }
        
        -- 1.3.6.1.4.1.2011.5.11.12.1
        hwCesECSThresholdControlEntry OBJECT-TYPE
            SYNTAX HwCesECSThresholdControlEntry
            MAX-ACCESS not-accessible
            STATUS current
            DESCRIPTION
                "E1 threshold enable table.
                 The indexes of this entry are ifIndex and hwCesECSMonitorPeriodType.
                "
            INDEX { ifIndex, hwCesECSMonitorPeriodType }
            ::= { hwCesECSThresholdControlTable 1 }
        
        HwCesECSThresholdControlEntry ::=
            SEQUENCE { 
                hwCesECSThresholdEnabled
                    INTEGER
             }

        -- 1.3.6.1.4.1.2011.5.11.12.1.1
        hwCesECSThresholdEnabled OBJECT-TYPE
            SYNTAX INTEGER
                {
                disable(0),
                enable(1)
                }
            MAX-ACCESS read-write
            STATUS current
            DESCRIPTION
                "E1 threshold enable.
                 Options:
                 1. disable(0)    - Disable the E1 threshold 
                 2. enable(1)     - Enable the E1 threshold
                "
            ::= { hwCesECSThresholdControlEntry 1 }
        
--E1 monitor threshold table
        -- 1.3.6.1.4.1.2011.5.11.13
        hwCesECSThresholdTable OBJECT-TYPE
            SYNTAX SEQUENCE OF HwCesECSThresholdEntry
            MAX-ACCESS not-accessible
            STATUS current
            DESCRIPTION
                "E1 monitor threshold table.
                 The indexes of this table are ifIndex and hwCesECSMonitorPeriodType.
                "
            ::= { hwCes 13 }
        
        -- 1.3.6.1.4.1.2011.5.11.13.1
        hwCesECSThresholdEntry OBJECT-TYPE
            SYNTAX HwCesECSThresholdEntry
            MAX-ACCESS not-accessible
            STATUS current
            DESCRIPTION
                "E1 monitor threshold table.
                 The indexes of this entry are ifIndex and hwCesECSMonitorPeriodType.
                "
            INDEX { ifIndex, hwCesECSMonitorPeriodType }
            ::= { hwCesECSThresholdTable 1 }
        
        HwCesECSThresholdEntry ::=
            SEQUENCE { 
                hwCesECSThresholdLowES
                    Gauge32,
                hwCesECSThresholdHighES
                    Gauge32,
                hwCesECSThresholdSES
                    Gauge32,
                hwCesECSThresholdUAS
                    Gauge32,
                hwCesECSThresholdCESC
                    Gauge32
             }

        -- 1.3.6.1.4.1.2011.5.11.13.1.1
        hwCesECSThresholdLowES OBJECT-TYPE
            SYNTAX Gauge32
            MAX-ACCESS read-write
            STATUS current
            DESCRIPTION
                "Errored seconds low threshold."
            ::= { hwCesECSThresholdEntry 1 }
        
        -- 1.3.6.1.4.1.2011.5.11.13.1.2
        hwCesECSThresholdHighES OBJECT-TYPE
            SYNTAX Gauge32
            MAX-ACCESS read-write
            STATUS current
            DESCRIPTION
                "Errored seconds high threshold."
            ::= { hwCesECSThresholdEntry 2 }
        
        -- 1.3.6.1.4.1.2011.5.11.13.1.3
        hwCesECSThresholdSES OBJECT-TYPE
            SYNTAX Gauge32
            MAX-ACCESS read-write
            STATUS current
            DESCRIPTION
                "Severely errored seconds threshold."
            ::= { hwCesECSThresholdEntry 3 }
        
        -- 1.3.6.1.4.1.2011.5.11.13.1.4
        hwCesECSThresholdUAS OBJECT-TYPE
            SYNTAX Gauge32
            MAX-ACCESS read-write
            STATUS current
            DESCRIPTION
                "Unavailable seconds threshold."
            ::= { hwCesECSThresholdEntry 4 }
        
        -- 1.3.6.1.4.1.2011.5.11.13.1.5
        hwCesECSThresholdCESC OBJECT-TYPE
            SYNTAX Gauge32
            MAX-ACCESS read-write
            STATUS current
            DESCRIPTION
                "Consecutive severely errored seconds threshold."
            ::= { hwCesECSThresholdEntry 5 }
        
--E1 perform monitor statistic table
        -- 1.3.6.1.4.1.2011.5.11.14
        hwCesECSDateTable OBJECT-TYPE
            SYNTAX SEQUENCE OF HwCesECSDateEntry
            MAX-ACCESS not-accessible
            STATUS current
            DESCRIPTION
                "E1 perform monitor statistic table.
                 The indexes of this table are ifIndex, hwCesECSMonitorPeriodType and hwCesECSMonitorStage. 
                "
            ::= { hwCes 14 }
        
        -- 1.3.6.1.4.1.2011.5.11.14.1
        hwCesECSDateEntry OBJECT-TYPE
            SYNTAX HwCesECSDateEntry
            MAX-ACCESS not-accessible
            STATUS current
            DESCRIPTION
                "E1 perform monitor statistic table.
                 The indexes of this entry are ifIndex, hwCesECSMonitorPeriodType and hwCesECSMonitorStage.
                "
            INDEX { ifIndex, hwCesECSMonitorPeriodType, hwCesECSMonitorStage }
            ::= { hwCesECSDateTable 1 }
        
        HwCesECSDateEntry ::=
            SEQUENCE { 
                hwCesECSMonitorStage
                    INTEGER,
                hwCesECSMonitorStageStartTime
                    DateAndTime,
                hwCesECSDataES
                    Gauge32,
                hwCesECSDataSES
                    Gauge32,
                hwCesECSDataUAS
                    Gauge32
             }

        -- 1.3.6.1.4.1.2011.5.11.14.1.1
        hwCesECSMonitorStage  OBJECT-TYPE
            SYNTAX INTEGER
                {
                current(0),
                history(1)
                }
            MAX-ACCESS read-only
            STATUS current
            DESCRIPTION
                "Perform monitor period stage, 0:current, 1:history
                 Options:
                 1. current(0) - The perform monitor period is current
                 2. history(1) - The perform monitor period is history
                "
            ::= { hwCesECSDateEntry 1 }
        
        -- 1.3.6.1.4.1.2011.5.11.14.1.2
        hwCesECSMonitorStageStartTime OBJECT-TYPE
            SYNTAX DateAndTime
            MAX-ACCESS read-only
            STATUS current
            DESCRIPTION
                "The start time of the monitor period."
            ::= { hwCesECSDateEntry 2 }
        
        -- 1.3.6.1.4.1.2011.5.11.14.1.3
        hwCesECSDataES OBJECT-TYPE
            SYNTAX Gauge32
            MAX-ACCESS read-only
            STATUS current
            DESCRIPTION
                "Statistic of the errored seconds."
            ::= { hwCesECSDateEntry 3 }
        
        -- 1.3.6.1.4.1.2011.5.11.14.1.4
        hwCesECSDataSES OBJECT-TYPE
            SYNTAX Gauge32
            MAX-ACCESS read-only
            STATUS current
            DESCRIPTION
                "Statistic of the severe errors."
            ::= { hwCesECSDateEntry 4 }
        
        -- 1.3.6.1.4.1.2011.5.11.14.1.5
        hwCesECSDataUAS OBJECT-TYPE
            SYNTAX Gauge32
            MAX-ACCESS read-only
            STATUS current
            DESCRIPTION
                "Statistic of the unavailable seconds."
            ::= { hwCesECSDateEntry 5 }
        
        -- 1.3.6.1.4.1.2011.5.11.15
        hwAtmCesSubboardWorkModeTable OBJECT-TYPE
            SYNTAX SEQUENCE OF HwAtmCesSubboardWorkModeEntry
            MAX-ACCESS not-accessible
            STATUS current
            DESCRIPTION
                "CES board configration table.
                 The indexes of this table are hwFrameIndex and hwSlotIndex.
                "
            ::= { hwCes 15 }
        
        -- 1.3.6.1.4.1.2011.5.11.15.1
        hwAtmCesSubboardWorkModeEntry OBJECT-TYPE
            SYNTAX HwAtmCesSubboardWorkModeEntry
            MAX-ACCESS not-accessible
            STATUS current
            DESCRIPTION          
                "CES board configration table.
                 The indexes of this entry are hwFrameIndex and hwSlotIndex.
                "
            INDEX { hwFrameIndex, hwSlotIndex }
            ::= { hwAtmCesSubboardWorkModeTable 1 }
        
        HwAtmCesSubboardWorkModeEntry ::=
            SEQUENCE { 
                hwAtmCesSubboardWorkMode
                    INTEGER
             }

        -- 1.3.6.1.4.1.2011.5.11.15.1.1
        hwAtmCesSubboardWorkMode OBJECT-TYPE
            SYNTAX INTEGER
                {
                loadsharing(1),
                activestandby(2)
                }
            MAX-ACCESS read-write
            STATUS current
            DESCRIPTION
                "CES subboard working mode.
                 Options:
                 1. loadsharing(1)   - The CES subboard works in loadsharing mode
                 2. activestandby(2) - The CES subboard works in activestandby mode
                "
            ::= { hwAtmCesSubboardWorkModeEntry 1 }
        
        -- 1.3.6.1.4.1.2011.5.11.16
        hwCesECSThresholdParameterTable OBJECT IDENTIFIER ::= { hwCes 16 }
        
        -- 1.3.6.1.4.1.2011.5.11.16.1
        hwCesErroredSeconds OBJECT-TYPE
            SYNTAX Integer32 (1..3600)
            MAX-ACCESS read-write
            STATUS current
            DESCRIPTION
                "Errored seconds degrade threshold."
            ::= { hwCesECSThresholdParameterTable 1 }
        
        -- 1.3.6.1.4.1.2011.5.11.16.2
        hwCesConsecutiveSeverelyErroredSeconds OBJECT-TYPE
            SYNTAX Integer32 (1..60)
            MAX-ACCESS read-write
            STATUS current
            DESCRIPTION
                "Consecutive severely errored seconds degrade threshold."
        
            ::= { hwCesECSThresholdParameterTable 2 }
        
        -- 1.3.6.1.4.1.2011.5.11.16.3
        hwCesDegradedMinutes OBJECT-TYPE
            SYNTAX Integer32 (1..60)
            MAX-ACCESS read-write
            STATUS current
            DESCRIPTION
                "Degraded Minutes degrade threshold."
        
            ::= { hwCesECSThresholdParameterTable 3 }
        
        -- 1.3.6.1.4.1.2011.5.11.16.4
        hwCesPortUnconditionalLineFailureErroredRate OBJECT-TYPE
            SYNTAX Integer32 (1000..9999)
            MAX-ACCESS read-write
            STATUS current
            DESCRIPTION
                "Line Unconditional Blooey Errored Rate threshold."
        
            ::= { hwCesECSThresholdParameterTable 4 }
        
        -- 1.3.6.1.4.1.2011.5.11.16.5
        hwCesPortOptionalLineFailureErroredRate OBJECT-TYPE
            SYNTAX Integer32 (10000..99999)
            MAX-ACCESS read-write
            STATUS current
            DESCRIPTION
                "Line Conditional Blooey Errored Rate threshold."  
        
            ::= { hwCesECSThresholdParameterTable 5 }
        
        -- 1.3.6.1.4.1.2011.5.11.16.6
        hwCesPortLineDisturbanceTransientErroredRate OBJECT-TYPE
            SYNTAX Integer32 (100000..999999)
            MAX-ACCESS read-write
            STATUS current
            DESCRIPTION
                "Line Temporary Disturb Errored Rate threshold."             
            ::= { hwCesECSThresholdParameterTable 6 }
        
        -- 1.3.6.1.4.1.2011.5.11.16.7
        hwCesPortG704ExcessiveFrameSlipfrequency OBJECT-TYPE
            SYNTAX Integer32 (1..100)
            MAX-ACCESS read-write
            STATUS current
            DESCRIPTION
                "Overfull Frame Slip threshold."

            ::= { hwCesECSThresholdParameterTable 7 }
        
        -- 1.3.6.1.4.1.2011.5.11.16.8
        hwCesDefinedErroredSeconds OBJECT-TYPE
            SYNTAX Integer32 (1..100)
            MAX-ACCESS read-write
            STATUS current
            DESCRIPTION
                "Errored Seconds Define threshold."
            ::= { hwCesECSThresholdParameterTable 8 }
        
        -- 1.3.6.1.4.1.2011.5.11.16.9
        hwCesDefinedSeverelyErroredSeconds OBJECT-TYPE
            SYNTAX Integer32 (1..100)
            MAX-ACCESS read-write
            STATUS current
            DESCRIPTION
                "Severely Errored Seconds Define threshold."
            ::= { hwCesECSThresholdParameterTable 9 }
        
        -- 1.3.6.1.4.1.2011.5.11.16.10
        hwCesDefinedDegradedMinutes OBJECT-TYPE
            SYNTAX Integer32 (1..256)
            MAX-ACCESS read-write
            STATUS current
            DESCRIPTION
                "Degraded Minutes Define threshold."
            ::= { hwCesECSThresholdParameterTable 10 }
        
        -- 1.3.6.1.4.1.2011.5.11.17
        hwAtmCesPortCESoPCLKTable OBJECT-TYPE
            SYNTAX SEQUENCE OF HwAtmCesPortCESoPCLKEntry
            MAX-ACCESS not-accessible
            STATUS current
            DESCRIPTION
                "Adaptive clock source configuration table.
                 The indexes of this table are hwFrameIndex, hwSlotIndex and hwAtmCesPortCESoPCLKIndex.
                "
            ::= { hwCes 17 }
        
        -- 1.3.6.1.4.1.2011.5.11.17.1
        hwAtmCesPortCESoPCLKEntry OBJECT-TYPE
            SYNTAX HwAtmCesPortCESoPCLKEntry
            MAX-ACCESS not-accessible
            STATUS current
            DESCRIPTION
                "Adaptive clock source configuration table.
                 The indexes of this entry are hwFrameIndex, hwSlotIndex and hwAtmCesPortCESoPCLKIndex.
                "
            INDEX { hwFrameIndex, hwSlotIndex, hwAtmCesPortCESoPCLKIndex }
            ::= { hwAtmCesPortCESoPCLKTable 1 }
        
        HwAtmCesPortCESoPCLKEntry ::=
            SEQUENCE { 
                hwAtmCesPortCESoPCLKIndex
                    Integer32,
                hwAtmCesPortCESoPCLKBindPW
                    Unsigned32,
                hwAtmCesPortCESoPCLKSetFlag
                    INTEGER,
                hwAtmCesPortCESoPCLKState
                    INTEGER,
                hwAtmCesPortCESoPLineCLKPortId
                    Integer32,
                hwAtmCesPortCESoPLineCLKState
                    INTEGER
             }

        -- 1.3.6.1.4.1.2011.5.11.17.1.1
        hwAtmCesPortCESoPCLKIndex OBJECT-TYPE
            SYNTAX Integer32 (0..15)
            MAX-ACCESS not-accessible
            STATUS current
            DESCRIPTION
                "The index of adaptive clock source."
            ::= { hwAtmCesPortCESoPCLKEntry 1 }
        
        -- 1.3.6.1.4.1.2011.5.11.17.1.2
        hwAtmCesPortCESoPCLKBindPW OBJECT-TYPE
            SYNTAX Unsigned32 (0..4294967294)
            MAX-ACCESS read-write
            STATUS current
            DESCRIPTION
                "Set and get the Connection ID binding with the adaptive clock source."
            ::= { hwAtmCesPortCESoPCLKEntry 2 }
        
        -- 1.3.6.1.4.1.2011.5.11.17.1.3
        hwAtmCesPortCESoPCLKSetFlag OBJECT-TYPE
            SYNTAX INTEGER
                {
                null(1),
                exist(2)
                }
            MAX-ACCESS read-write
            STATUS current
            DESCRIPTION
                "Get and set the configuration of adaptive clock source.
                 Options:
                 1. null(1)         - The clock source is null
                 2. exist(2)        - The clock source exist
                "
            ::= { hwAtmCesPortCESoPCLKEntry 3 }
        
        -- 1.3.6.1.4.1.2011.5.11.17.1.4
        hwAtmCesPortCESoPCLKState OBJECT-TYPE
            SYNTAX INTEGER
                {
                normal(1),
                fault(2)
                }
            MAX-ACCESS read-only
            STATUS current
            DESCRIPTION
                "Get the running state of adaptive clock source.
                 Options:
                 1. normal(1) - Normal state
                 2. fault(2)  - Fault state
                "
            ::= { hwAtmCesPortCESoPCLKEntry 4 }
            
        -- 1.3.6.1.4.1.2011.5.11.17.1.5
        hwAtmCesPortCESoPLineCLKPortId OBJECT-TYPE
            SYNTAX Integer32 (0..15)
            MAX-ACCESS read-write
            STATUS current
            DESCRIPTION
                "Set and get the Port ID binding with the Line clock source."
            ::= { hwAtmCesPortCESoPCLKEntry 5 }
            
        -- 1.3.6.1.4.1.2011.5.11.17.1.6
        hwAtmCesPortCESoPLineCLKState OBJECT-TYPE
            SYNTAX INTEGER
                {
                normal(1),
                fault(2)
                }
            MAX-ACCESS read-only
            STATUS current
            DESCRIPTION
                "Get the running state of Line clock source.
                 Options:
                 1. normal(1) - Normal state
                 2. fault(2)  - Fault state
                "
            ::= { hwAtmCesPortCESoPCLKEntry 6 }
            
        -- 1.3.6.1.4.1.2011.5.11.18
        hwCesTDMVCLCfgTable OBJECT-TYPE
            SYNTAX SEQUENCE OF HwCesTDMVCLCfgEntry
            MAX-ACCESS not-accessible
            STATUS current
            DESCRIPTION
                "TDM VCL configuration table.
                 The indexes of this table are hwTDMVCLID and ifIndex.
                "
            ::= { hwCes 18 }        
        -- 1.3.6.1.4.1.2011.5.11.18.1
        hwCesTDMVCLCfgEntry OBJECT-TYPE
            SYNTAX HwCesTDMVCLCfgEntry
            MAX-ACCESS not-accessible
            STATUS current
            DESCRIPTION
                "TDM VCL configuration table.
                 The indexes of this entry are hwTDMVCLID and ifIndex.
                "
            INDEX { hwTDMVCLID, ifIndex }
            ::= { hwCesTDMVCLCfgTable 1 }
        
        HwCesTDMVCLCfgEntry ::=
            SEQUENCE { 
                hwTDMVCLID
                    Unsigned32,
                hwTDMVCLType
                    INTEGER,
                hwTDMVCLTimeslot
                    Unsigned32,
                hwTDMVCLRowStatus
                    RowStatus
             }
             
        -- 1.3.6.1.4.1.2011.5.11.18.1.1
        hwTDMVCLID OBJECT-TYPE
            SYNTAX Unsigned32 (0..4294967294)
            MAX-ACCESS not-accessible
            STATUS current
            DESCRIPTION
                "TDM VCL ID."
            ::= { hwCesTDMVCLCfgEntry 1 }
            
        -- 1.3.6.1.4.1.2011.5.11.18.1.2
        hwTDMVCLType OBJECT-TYPE
            SYNTAX INTEGER
                {
                satop(1),
                cesop(2)
                }
            MAX-ACCESS read-write
            STATUS current
            DESCRIPTION
                "TDM VCL type.
                 Options:
                 1. satop(1) - The TDM VCL Type is satop
                 2. cesop(2) - The TDM VCL Type is cesop
                "
            ::= { hwCesTDMVCLCfgEntry 2 }
            
        -- 1.3.6.1.4.1.2011.5.11.18.1.3
        hwTDMVCLTimeslot OBJECT-TYPE
            SYNTAX Unsigned32
            MAX-ACCESS read-write
            STATUS current
            DESCRIPTION
                "TDM timeslot, it must be set if hwTDMVCLType is set to be cesop."
            ::= { hwCesTDMVCLCfgEntry 3 }
            
        hwTDMVCLRowStatus OBJECT-TYPE
            SYNTAX RowStatus
            MAX-ACCESS read-write
            STATUS current
            DESCRIPTION
                "Row operation node . Running status cannot be deleted."
            ::= { hwCesTDMVCLCfgEntry 4 }


    hwCesTrapsVbOids      OBJECT IDENTIFIER ::= { hwCes 19 }
    
    hwAtmCesPortStatus OBJECT-TYPE
        SYNTAX INTEGER
		{
		    normal(1),
		    test(2),
		    idle(3),
		    notExisted(4),
		    fail(5),
		    block(6),
		    maintain(7),
		    loopback(11)
		}
        MAX-ACCESS accessible-for-notify
        STATUS current
        DESCRIPTION 
                "Indicate the port state.
                 Options:
                 1. normal(1)       - The port is in normal state
		 2. test(2)         - The port is in test state
		 3. idle(3)         - The port is in idle state
		 4. notExisted(4)   - The port doesn't exist
		 5. fail(5)         - The port is in fail state
		 6. block(6)        - The port is in block state
		 7. maintain(7)     - The port is in maintain state
		 8. loopback(11)    - The port is in loopback state
                "
    ::= { hwCesTrapsVbOids 1 }

-- ces trap
        
        hwCesTraps         OBJECT IDENTIFIER ::= { hwCes 20 }
        hwCesCommonTraps      OBJECT IDENTIFIER ::= { hwCesTraps 1 }
        hwCesCommonTrapsPrefix      OBJECT IDENTIFIER ::= { hwCesCommonTraps 0 }
         
        hwCesPortStatusTrap NOTIFICATION-TYPE
            OBJECTS 
                {
                hwFrameIndex,
                hwSlotIndex,
                hwPortIndex,
                hwAtmCesPortStatus
                } 
            STATUS current
            DESCRIPTION
                "This trap message is generated when Ces port status changed."
            ::= { hwCesCommonTraps 0 1 }
     
        hwCesBoardWorkModeChangeTrap NOTIFICATION-TYPE
            OBJECTS 
                {
                hwConfigChangeIP,
                hwFrameIndex,
                hwSlotIndex,
                hwAtmCesCfgAccessMode           
                } 
            STATUS current
            DESCRIPTION
                "This trap message is generated when E1T1 board work mode changed."
            ::= { hwCesCommonTraps 0 2 }
        
        hwCesPortWorkModeChangeTrap NOTIFICATION-TYPE
            OBJECTS 
                {
                hwConfigChangeIP,
                hwFrameIndex,
                hwSlotIndex,
                hwPortIndex,
                hwAtmCesPortCfgWorkMode,
                hwAtmCesPortCfgClockMode,
                hwAtmCesPortCfgSignalType,
                hwAtmCesPortCfgFrameVerifyMode,
                hwAtmCesPortAcmSource           
                } 
            STATUS current
            DESCRIPTION
                "This trap message is generated when Ces port work mode changed."
            ::= { hwCesCommonTraps 0 3 }      

        hwCesAlarmTraps  OBJECT IDENTIFIER ::= { hwCesTraps 2 }
        hwCesAlarmTrapsPrefix  OBJECT IDENTIFIER ::= { hwCesAlarmTraps 0 }
        hwCesPortSignalLossAlarmTrap NOTIFICATION-TYPE
            OBJECTS 
                {
                hwFrameIndex,
                hwSlotIndex,
                hwPortIndex
                } 
            STATUS current
            DESCRIPTION
                "This trap message is generated when Loss of signal occurs at the E1/T1 port."
            ::= { hwCesAlarmTraps 0 1 }
        
        hwCesFrameLossAlarmTrap NOTIFICATION-TYPE
            OBJECTS 
                {
                hwFrameIndex,
                hwSlotIndex,
                hwPortIndex
                } 
            STATUS current
            DESCRIPTION
                "This trap message is generated when Loss of frame alignment occurs at the E1/T1 port."
            ::= { hwCesAlarmTraps 0 2 }
    
        hwCesRemoteAlarmReceivedAlarmTrap NOTIFICATION-TYPE
            OBJECTS 
                {
                hwFrameIndex,
                hwSlotIndex,
                hwPortIndex
                } 
            STATUS current
            DESCRIPTION
                "This trap message is generated when remote alarm occurs at the E1/T1 port."
            ::= { hwCesAlarmTraps 0 3 }
    
        hwCesMultiframeLossAlarmTrap NOTIFICATION-TYPE
            OBJECTS 
                {
                hwFrameIndex,
                hwSlotIndex,
                hwPortIndex
                } 
            STATUS current
            DESCRIPTION
                "This trap message is generated when Loss of multiframe alignment occurs at the E1/T1 port."
            ::= { hwCesAlarmTraps 0 4 }
    
        hwCesSignalOccurAlarmTrap NOTIFICATION-TYPE
            OBJECTS 
                {
                hwFrameIndex,
                hwSlotIndex,
                hwPortIndex
                } 
            STATUS current
            DESCRIPTION
                "This trap message is generated when signal occurs at the E1/T1 port."
            ::= { hwCesAlarmTraps 0 5 }
    
        hwCesCRC4ErrorOccurAlarmTrap NOTIFICATION-TYPE
            OBJECTS 
                {
                hwFrameIndex,
                hwSlotIndex,
                hwPortIndex
                } 
            STATUS current
            DESCRIPTION
                "This trap message is generated when CRC4 error occurs at the E1/T1 port."
            ::= { hwCesAlarmTraps 0 6 }
        
        hwCesLOSRecoverAlarmTrap NOTIFICATION-TYPE
            OBJECTS 
                {
                hwFrameIndex,
                hwSlotIndex,
                hwPortIndex
                } 
            STATUS current
            DESCRIPTION
                "This trap message is generated when Loss of signal(LOS) recover at the E1/T1 port."
            ::= { hwCesAlarmTraps 0 7 }
    
        hwCesFrameRecoverAlarmTrap NOTIFICATION-TYPE
            OBJECTS 
                {
                hwFrameIndex,
                hwSlotIndex,
                hwPortIndex
                } 
            STATUS current
            DESCRIPTION
                "This trap message is generated when Loss of frame recover at the E1/T1 port."
            ::= { hwCesAlarmTraps 0 8 }
        
        hwCesRemoteAlarmRecoverAlarmTrap NOTIFICATION-TYPE
            OBJECTS 
                {
                hwFrameIndex,
                hwSlotIndex,
                hwPortIndex
                } 
            STATUS current
            DESCRIPTION
                "This trap message is generated when Remote alarm recover at the E1/T1 port."
            ::= { hwCesAlarmTraps 0 9 }
                    
        hwCesMultiframeRecoverAlarmTrap NOTIFICATION-TYPE
            OBJECTS 
                {
                hwFrameIndex,
                hwSlotIndex,
                hwPortIndex
                } 
            STATUS current
            DESCRIPTION
                "This trap message is generated when Loss of multiframe alignment recover at the E1/T1 port."
            ::= { hwCesAlarmTraps 0 10 }
        
        hwCesSignalRecoverAlarmTrap NOTIFICATION-TYPE
            OBJECTS 
                {
                hwFrameIndex,
                hwSlotIndex,
                hwPortIndex
                } 
            STATUS current
            DESCRIPTION
                "This trap message is generated when signal recover at the E1/T1 port."
            ::= { hwCesAlarmTraps 0 11 }
        
        hwCesCRC4RecoverAlarmTrap NOTIFICATION-TYPE
            OBJECTS 
                {
                hwFrameIndex,
                hwSlotIndex,
                hwPortIndex
                } 
            STATUS current
            DESCRIPTION
                "This trap message is generated when CRC4 recover at the E1/T1 port."
            ::= { hwCesAlarmTraps 0 12 }
    
        hwCesACMClockRestoreAlarmTrap NOTIFICATION-TYPE
            OBJECTS 
                {
                hwFrameIndex,
                hwSlotIndex,
                hwAtmCesPortCESoPCLKIndex
                } 
            STATUS current
            DESCRIPTION
               "This trap message is generated when ACM clock restore."
            ::= { hwCesAlarmTraps 0 13 }
        
        hwCesACMClockFaultAlarmTrap NOTIFICATION-TYPE
            OBJECTS 
                {
                hwFrameIndex,
                hwSlotIndex,
                hwAtmCesPortCESoPCLKIndex
                } 
            STATUS current
            DESCRIPTION
                "This trap message is generated when ACM clock fault."
            ::= { hwCesAlarmTraps 0 14 }        

        -- 1.3.6.1.4.1.2011.5.11.21
        hwCesOnuTDMVCLCfgTable OBJECT-TYPE
            SYNTAX SEQUENCE OF HwCesOnuTDMVCLCfgEntry
            MAX-ACCESS not-accessible
            STATUS current
            DESCRIPTION
                "This table is used for setting ONU TDM VCL.
                 The indexes of this table are hwOnuTDMVCLIfindex, hwOnuTDMVCLOnuId and hwOnuTDMVCLID.
                "
            ::= { hwCes 21 }    
                
        -- 1.3.6.1.4.1.2011.5.11.21.1
        hwCesOnuTDMVCLCfgEntry OBJECT-TYPE
            SYNTAX HwCesOnuTDMVCLCfgEntry
            MAX-ACCESS not-accessible
            STATUS current
            DESCRIPTION
                "This table is used for setting ONU TDM VCL.
                 The indexes of this entry are hwOnuTDMVCLIfindex, hwOnuTDMVCLOnuId and hwOnuTDMVCLID.
                "
            INDEX { hwOnuTDMVCLIfindex, hwOnuTDMVCLOnuId, hwOnuTDMVCLID }
            ::= { hwCesOnuTDMVCLCfgTable 1 }
        
        HwCesOnuTDMVCLCfgEntry ::=
            SEQUENCE { 
                hwOnuTDMVCLIfindex
                        Unsigned32,
                hwOnuTDMVCLOnuId
                        Unsigned32,
                hwOnuTDMVCLID
                        Integer32,
                hwOnuTDMVCLPortId
                        Unsigned32,
                hwOnuTDMVCLType
                        INTEGER,
                hwOnuTDMVCLTimeSlot
                        Unsigned32,
                hwOnuTDMVCLRowStatus
                        RowStatus
             }
             
        -- 1.3.6.1.4.1.2011.5.11.21.1.1
        hwOnuTDMVCLIfindex OBJECT-TYPE
            SYNTAX Unsigned32 (0..4294967294)
            MAX-ACCESS not-accessible
            STATUS current
            DESCRIPTION
                "It is one of the table indexes. Indicates the interface index."
            ::= { hwCesOnuTDMVCLCfgEntry 1 }
            
        -- 1.3.6.1.4.1.2011.5.11.21.1.2
        hwOnuTDMVCLOnuId OBJECT-TYPE
            SYNTAX Unsigned32 (0..4294967294)
            MAX-ACCESS not-accessible
            STATUS current
            DESCRIPTION
                "It is one of the table indexes. Indicates the ONU ID."
            ::= { hwCesOnuTDMVCLCfgEntry 2 }
            
        -- 1.3.6.1.4.1.2011.5.11.21.1.3
        hwOnuTDMVCLID OBJECT-TYPE
            SYNTAX Integer32 (-1..2147483647)
            MAX-ACCESS not-accessible
            STATUS current
            DESCRIPTION
                "It is one of the table indexes. Indicates the ONU TDM VCL ID. 
                 -1 indicates that the ID will be allocated dynamically."
            ::= { hwCesOnuTDMVCLCfgEntry 3 }
            
        -- 1.3.6.1.4.1.2011.5.11.21.1.4
        hwOnuTDMVCLPortId OBJECT-TYPE
            SYNTAX Unsigned32 (0..4294967294)
            MAX-ACCESS read-write
            STATUS current
            DESCRIPTION
                "Indicates the ONU port ID."
            ::= { hwCesOnuTDMVCLCfgEntry 4 }
            
        -- 1.3.6.1.4.1.2011.5.11.21.1.5
        hwOnuTDMVCLType OBJECT-TYPE
            SYNTAX INTEGER
                {
                satop(1),
                cesop(2)
                }
            MAX-ACCESS read-write
            STATUS current
            DESCRIPTION
                "TDM VCL type.
                 Options:
                 1. satop(1) - The ONU TDM VCL Type is satop
                 2. cesop(2) - The ONU TDM VCL Type is cesop
                "
            ::= { hwCesOnuTDMVCLCfgEntry 5 }
            
        -- 1.3.6.1.4.1.2011.5.11.21.1.6
        hwOnuTDMVCLTimeSlot OBJECT-TYPE
            SYNTAX Unsigned32 (0..4294967294)
            MAX-ACCESS read-write
            STATUS current
            DESCRIPTION
                "TDM timeslot, it must be set if hwOnuTDMVCLType is set to be cesop."
            ::= { hwCesOnuTDMVCLCfgEntry 6 }
            
        -- 1.3.6.1.4.1.2011.5.11.21.1.7    
        hwOnuTDMVCLRowStatus OBJECT-TYPE
            SYNTAX RowStatus
            MAX-ACCESS read-write
            STATUS current
            DESCRIPTION
                "Row operation node. Running status cannot be deleted."
            ::= { hwCesOnuTDMVCLCfgEntry 7 }
        
        END
