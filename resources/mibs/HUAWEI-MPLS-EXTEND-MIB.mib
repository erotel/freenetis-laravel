-- ==================================================================
-- Copyright (C) 2011 by HUAWEI TECHNOLOGIES. All rights reserved.
-- Description:   This MIB is used for defining the HUAWEI private   
--                extended Multiprotocol Label Switching (MPLS) MIB 
--                object. All MIB objects are used to describe private
--                managed objects and trap definitions for MPLS.
-- Reference:
-- Version: V2.00
-- History:
-- V2.00 YuPingping, 2011-07-30, revision

-- ==================================================================
-- ==================================================================
-- 
-- Variables and types be imported
-- 
-- ==================================================================

    HUAWEI-MPLS-EXTEND-MIB DEFINITIONS ::= BEGIN
 
        IMPORTS
            hwDatacomm            
                FROM HUAWEI-MIB            
            ifIndex, ifName           
                FROM IF-MIB            
            MplsIndexType            
                FROM MPLS-LSR-STD-MIB            
            MplsTunnelIndex, MplsTunnelInstanceIndex, MplsExtendedTunnelId            
                FROM MPLS-TC-STD-MIB            
            SnmpAdminString            
                FROM SNMP-FRAMEWORK-MIB            
            OBJECT-GROUP, NOTIFICATION-GROUP            
                FROM SNMPv2-CONF            
            Integer32, Unsigned32, Counter32, BITS, OBJECT-TYPE, 
            MODULE-IDENTITY, NOTIFICATION-TYPE            
                FROM SNMPv2-SMI;
    
    

        -- 1.3.6.1.4.1.2011.5.25.121
        hwMplsExtendMib MODULE-IDENTITY 
            LAST-UPDATED "201107301100Z"        
            ORGANIZATION 
                "Multiprotocol Label Switching (MPLS) Working Group"
            CONTACT-INFO 
                "MPLS Team Huawei Technologies co.,Ltd.
                Huawei Bld.,NO.3 Xinxi Rd., 
                Shang-Di Information Industry Base,
                Hai-Dian District Beijing P.R. China
                http://www.huawei.com
                Zip:100085
                Email:support@huawei.com
		"
            DESCRIPTION 
                "This MIB is used for defining the HUAWEI private   
                 extended Multiprotocol Label Switching (MPLS) MIB
                 object. All MIB objects are used to describe private
                 managed objects and trap definitions for MPLS."
                                
            --  Revision history    
            REVISION    "201107301100Z"  
            DESCRIPTION "V2.00, delete Delval clause in these nodes: hwMplsTunnelDownReason, hwMplsTunnelLspType."
            
	    REVISION     "201011231155Z"        
            DESCRIPTION  "V1.02, modified the MIB description."
                                        
            REVISION     "201007131535Z"        
            DESCRIPTION  "V1.01, modified the MIB description."
            
            REVISION     "200606301554Z"       
            DESCRIPTION  "V1.00, initial LSPM MIB."
            ::= { hwDatacomm 121 }

        
    
    
--
-- Node definitions
--
    
-- 1.3.6.1.4.1.2011.5.25.121.1
        hwMplsExtendMibTunnel OBJECT IDENTIFIER ::= { hwMplsExtendMib 1 }

--   1.3.6.1.4.1.2011.5.25.121.1.1
        hwMplsTunnelTable OBJECT-TYPE
            SYNTAX SEQUENCE OF HwMplsTunnelEntry
            MAX-ACCESS not-accessible
            STATUS current
            DESCRIPTION
                "A tunnel needs to be uniquely identified across  
                 an MPLS network. Indexes hwMplsTunnelIndex and       
                 hwMplsTunnelInstance uniquely identify a tunnel 
                 on the LSR originating the tunnel. 
                 hwMplsTunnelIngressLSRId uniquely identifies a 
                 tunnel across an MPLS network. The last index     
                 hwMplsTunnelEgressLSRId is useful in identifying
                 all instances of a tunnel that are terminated on
                 the same egress LSR.                                       
                 The indexes of this table are hwMplsTunnelIndex,    
                 hwMplsTunnelInstance, hwMplsTunnelIngressLSRId and  
                 hwMplsTunnelEgressLSRId."
            ::= { hwMplsExtendMibTunnel 1 }

--   1.3.6.1.4.1.2011.5.25.121.1.1.1
        hwMplsTunnelEntry OBJECT-TYPE
            SYNTAX HwMplsTunnelEntry
            MAX-ACCESS not-accessible
            STATUS current
            DESCRIPTION
                "A tunnel needs to be uniquely identified across  
                 an MPLS network. Indexes hwMplsTunnelIndex and       
                 hwMplsTunnelInstance uniquely identify a tunnel 
                 on the LSR originating the tunnel. 
                 hwMplsTunnelIngressLSRId uniquely identifies a 
                 tunnel across an MPLS network. The last index     
                 hwMplsTunnelEgressLSRId is useful in identifying
                 all instances of a tunnel that are terminated on
                 the same egress LSR.                                       
                 The indexes of this entry are hwMplsTunnelIndex,    
                 hwMplsTunnelInstance, hwMplsTunnelIngressLSRId and  
                 hwMplsTunnelEgressLSRId."
            REFERENCE
                "1. RFC 2863 - The Interfaces Group MIB, McCloghrie,
                K., and F. Kastenholtz, June 2000 "
            INDEX { hwMplsTunnelIndex, hwMplsTunnelInstance, hwMplsTunnelIngressLSRId, hwMplsTunnelEgressLSRId }
            ::= { hwMplsTunnelTable 1 }

        
        HwMplsTunnelEntry ::=
            SEQUENCE { 
                hwMplsTunnelIndex
                    MplsTunnelIndex,
                hwMplsTunnelInstance
                    MplsTunnelInstanceIndex,
                hwMplsTunnelIngressLSRId
                    MplsExtendedTunnelId,
                hwMplsTunnelEgressLSRId
                    MplsExtendedTunnelId,
                hwMplsTunnelClassType
                    INTEGER,
                hwMplsTunnelBandwidth
                    Integer32,
                hwMplsTunnelAdminStatus
                    INTEGER,
                hwMplsTunnelOperStatus
                    INTEGER,
                hwMplsTunnelSessionAttr
                    BITS,
                hwMplsTunnelFrrSetupPrio
                    Unsigned32,
                hwMplsTunnelFrrHoldingPrio
                    Unsigned32,
                hwMplsTunnelFrrBandwidth
                    Unsigned32,
                hwMplsTunnelFrrSwitchover
                    Counter32,
                hwMplsTunnelFrrBypassTableIndex
                    Unsigned32,
                hwMplsTunnelFrrARHopTableIndex
                    Unsigned32,
                hwMplsTunnelName
                    SnmpAdminString,
                hwMplsTunnelIfIndex
                    Unsigned32,
                hwMplsTunnelPreBandwidth
                    Unsigned32,
                hwMplsTunnelNextBandwidth
                    Unsigned32,
                hwMplsTunnelCt0Bandwidth
                    Unsigned32,
                hwMplsTunnelCt1Bandwidth
                    Unsigned32,
                hwMplsTunnelCt2Bandwidth
                    Unsigned32,
                hwMplsTunnelCt3Bandwidth
                    Unsigned32,
                hwMplsTunnelCt4Bandwidth
                    Unsigned32,
                hwMplsTunnelCt5Bandwidth
                    Unsigned32,
                hwMplsTunnelCt6Bandwidth
                    Unsigned32,
                hwMplsTunnelCt7Bandwidth
                    Unsigned32,
                hwMplsTunnelLspType
                    INTEGER,
                hwMplsTunnelInterfaceName
                    SnmpAdminString,
                hwMplsTunnelSignalProto
                    INTEGER
             }

--   1.3.6.1.4.1.2011.5.25.121.1.1.1.1
        hwMplsTunnelIndex OBJECT-TYPE
            SYNTAX MplsTunnelIndex
            MAX-ACCESS not-accessible
            STATUS current
            DESCRIPTION
                "Uniquely identifies a set of tunnel instances 
                between a pair of ingress and egress LSRs. 
                When the MPLS signalling protocol is rsvp(2), this value 
                equals to the value signaled in the Tunnel ID 
                of the SESSION object. When the MPLS signalling protocol 
                is crldp(3), this value equals to the value 
                signaled in the LSP ID. Reference to MPLS-TE-STD-MIB."
            ::= { hwMplsTunnelEntry 1 }

        
--   1.3.6.1.4.1.2011.5.25.121.1.1.1.2
        hwMplsTunnelInstance OBJECT-TYPE
            SYNTAX MplsTunnelInstanceIndex
            MAX-ACCESS not-accessible
            STATUS current
            DESCRIPTION
                "Uniquely identifies a particular instance of a 
                tunnel between a pair of ingress and egress LSRs. 
                It is used to identify multiple instances of 
                tunnels for backup and parallel tunnels. 
                When the MPLS signaling protocol is 
                rsvp(2), this value equals to the LSP ID 
                of the Sender Template object. When the signaling 
                protocol is crldp(3) there is no equivalent 
                signaling object. Reference to MPLS-TE-STD-MIB."
            ::= { hwMplsTunnelEntry 2 }

        
--   1.3.6.1.4.1.2011.5.25.121.1.1.1.3
        hwMplsTunnelIngressLSRId OBJECT-TYPE
            SYNTAX MplsExtendedTunnelId
            MAX-ACCESS not-accessible
            STATUS current
            DESCRIPTION
                "Indicates the ingress LSR ID of this tunnel. 
                When the MPLS signalling protocol 
                is rsvp(2), this value equals to the Tunnel 
                Sender Address in the Sender Template object and may 
                equal to the Extended Tunnel ID in the 
                SESSION object. When the MPLS signalling protocol is 
                crldp(3), this value equals to the Ingress 
                LSR Router ID in the LSPID TLV object. 
                Reference to MPLS-TE-STD-MIB."
            ::= { hwMplsTunnelEntry 3 }

        
--   1.3.6.1.4.1.2011.5.25.121.1.1.1.4
        hwMplsTunnelEgressLSRId OBJECT-TYPE
            SYNTAX MplsExtendedTunnelId
            MAX-ACCESS not-accessible
            STATUS current
            DESCRIPTION
                "Indicates the egress LSR ID of this 
                tunnel. Reference to MPLS-TE-STD-MIB."
            ::= { hwMplsTunnelEntry 4 }

        
--   1.3.6.1.4.1.2011.5.25.121.1.1.1.5
        hwMplsTunnelClassType OBJECT-TYPE
            SYNTAX INTEGER
                {
                bc0(1),
                bc1(2),
                invalidValue(3)
                }
            MAX-ACCESS read-only
            STATUS current
            DESCRIPTION
                "Indicates the bandwidth type used by this tunnel. 
                Options:
                1. bc0(1)          -indicates the bandwidth type is bc0.
                2. bc1(2)          -indicates the bandwidth type is bc1.
                3. invalidValue(3) -indicates the invalid value.
                "
            ::= { hwMplsTunnelEntry 5 }

        
--   1.3.6.1.4.1.2011.5.25.121.1.1.1.6
        hwMplsTunnelBandwidth OBJECT-TYPE
            SYNTAX Integer32
            MAX-ACCESS read-only
            STATUS current
            DESCRIPTION
                "Indicates the bandwidth used by this tunnel.
                Unit: kbit/s
                "
            ::= { hwMplsTunnelEntry 6 }

        
--   1.3.6.1.4.1.2011.5.25.121.1.1.1.7
        hwMplsTunnelAdminStatus OBJECT-TYPE
            SYNTAX INTEGER
                {
                up(1),
                down(2),
                testing(3)
                }
            MAX-ACCESS read-only
            STATUS current
            DESCRIPTION
                "Indicates the management status of this 
                tunnel.Reference to MPLS-TE-STD-MIB.
                Options:
                1. up(1)      -indicates the management status of this tunnel is up.
                2. down(2)    -indicates the management status of this tunnel is down.
                3. testing(3) -indicates the tunnel is used in some test mode.         
                "
            ::= { hwMplsTunnelEntry 7 }

        
--   1.3.6.1.4.1.2011.5.25.121.1.1.1.8
        hwMplsTunnelOperStatus OBJECT-TYPE
            SYNTAX INTEGER
                {
                up(1),
                down(2),
                testing(3),
                unknown(4),
                dormant(5),
                notPresent(6),
                lowerLayerDown(7)
                }
            MAX-ACCESS read-only
            STATUS current
            DESCRIPTION
                "Indicates the actual operational status of this tunnel, 
                which is but not limited to the status of this tunnel of
                a certain period.Reference to MPLS-TE-STD-MIB.
                Options:
                1. up(1)             -indicates that the operational status of this tunnel is up.          
                2. down(2)           -indicates that the operational status of this tunnel is down.
                3. testing(3)        -indicates that the tunnel is used in some test mode.
                4. unknown(4)        -indicates the invalid value.
                5. dormant(5)        -indicates that the status cannot be determined.
                6. notPresent(6)     -indicates that some component is missing
                7. lowerLayerDown(7) -indicates the Down state due to the state of lower layer interfaces.
                "
            ::= { hwMplsTunnelEntry 8 }

        
--   1.3.6.1.4.1.2011.5.25.121.1.1.1.9
        hwMplsTunnelSessionAttr OBJECT-TYPE
            SYNTAX BITS
                {
                localProtectionDesired(0),
                nodeProtectionDesired(1),
                bandwidthProtectionDesired(2)
                }
            MAX-ACCESS read-only
            STATUS current
            DESCRIPTION
                "Indicates protection types desired by the primary 
                tunnel, such as node protection, link protection or 
                bandwidth protection.
                Options:
                1. localProtectionDesired(0)     -indicates link protection.
                2. nodeProtectionDesired(1)      -indicates node protection.
                3. bandwidthProtectionDesired(2) -indicates bandwidth protection.              
                "
            ::= { hwMplsTunnelEntry 9 }

        
--   1.3.6.1.4.1.2011.5.25.121.1.1.1.10
        hwMplsTunnelFrrSetupPrio OBJECT-TYPE
            SYNTAX Unsigned32
            MAX-ACCESS read-only
            STATUS current
            DESCRIPTION
                "Indicates the setup PRI of auto-bypass tunnel.
                Range: 0-7
                Default: 7
                "
            ::= { hwMplsTunnelEntry 10 }

        
--   1.3.6.1.4.1.2011.5.25.121.1.1.1.11
        hwMplsTunnelFrrHoldingPrio OBJECT-TYPE
            SYNTAX Unsigned32
            MAX-ACCESS read-only
            STATUS current
            DESCRIPTION
                "Indicates the holding PRI of auto-bypass tunnel.
                Range: 0-7
                Default: 7
                "
            ::= { hwMplsTunnelEntry 11 }

        
--   1.3.6.1.4.1.2011.5.25.121.1.1.1.12
        hwMplsTunnelFrrBandwidth OBJECT-TYPE
            SYNTAX Unsigned32
            MAX-ACCESS read-only
            STATUS current
            DESCRIPTION
                "Indicates the protecting bandwidth of auto-bypass tunnel. 
                Its value is defined by the configuration on the primary 
                tunnel.
                Unit: kbit/s"
            ::= { hwMplsTunnelEntry 12 }

        
--   1.3.6.1.4.1.2011.5.25.121.1.1.1.13
        hwMplsTunnelFrrSwitchover OBJECT-TYPE
            SYNTAX Counter32
            MAX-ACCESS read-only
            STATUS current
            DESCRIPTION
                "Indicates FRR switching times"
            ::= { hwMplsTunnelEntry 13 }

        
--   1.3.6.1.4.1.2011.5.25.121.1.1.1.14
        hwMplsTunnelFrrBypassTableIndex OBJECT-TYPE
            SYNTAX Unsigned32
            MAX-ACCESS read-only
            STATUS current
            DESCRIPTION
                "Indicates the index of the bypass tunnel table, that is, 
                the LSP ID of the bypass tunnel. The bypass table shows 
                interfaces protected by specified bypass tunnel."
            ::= { hwMplsTunnelEntry 14 }

        
--   1.3.6.1.4.1.2011.5.25.121.1.1.1.15
        hwMplsTunnelFrrARHopTableIndex OBJECT-TYPE
            SYNTAX Unsigned32
            MAX-ACCESS read-only
            STATUS current
            DESCRIPTION
                "Indicates the table index of the protection type adopted 
                by each hop of the primary tunnel."
            ::= { hwMplsTunnelEntry 15 }
        
        hwMplsTunnelName OBJECT-TYPE
            SYNTAX SnmpAdminString
            MAX-ACCESS read-only
            STATUS current
            DESCRIPTION
                "Indicates the tunnel name. The name can refer to the tunnel 
                on the console port of the LSR. If mplsTunnelIsIf is set to 
                True, the IfName of the interface corresponding to this tunnel 
                should have a value equal to hwMplsTunnelName. 
                Reference to the description of IfName in RFC 2863."
            ::= { hwMplsTunnelEntry 16 }
        
        hwMplsTunnelIfIndex OBJECT-TYPE
            SYNTAX Unsigned32
            MAX-ACCESS read-only
            STATUS current
            DESCRIPTION
                "Indicates the interface index of the tunnel. It uniquely 
                identifies the tunnel name."
            ::= { hwMplsTunnelEntry 17 }

        
        hwMplsTunnelPreBandwidth OBJECT-TYPE
            SYNTAX Unsigned32
            MAX-ACCESS read-only
            STATUS current
            DESCRIPTION
                "Indicates the original bandwidth of the tunnel 
                when the tunnel is in the Modify state.
                Unit: kbit/s"
            ::= { hwMplsTunnelEntry 18 }

        
        hwMplsTunnelNextBandwidth OBJECT-TYPE
            SYNTAX Unsigned32
            MAX-ACCESS read-only
            STATUS current
            DESCRIPTION
                "Indicates the bandwidth of the tunnel that is to be changed 
                when the tunnel is in the Modify state.
                Unit: kbit/s"
            ::= { hwMplsTunnelEntry 19 }

        
        hwMplsTunnelCt0Bandwidth OBJECT-TYPE
            SYNTAX Unsigned32
            UNITS "kilobits per second"
            MAX-ACCESS read-only
            STATUS current
            DESCRIPTION
                "The bandwidth of Class-Type 0 (CT0) in this tunnel, in kbit/s.                
                If all CT bandwidths are 0s, it means that this tunnel's Class-Type
                is CT0, and bandwidth is 0 kbit/s.
                Unit: kbit/s"
            ::= { hwMplsTunnelEntry 20 }

        
        hwMplsTunnelCt1Bandwidth OBJECT-TYPE
            SYNTAX Unsigned32
            UNITS "kilobits per second"
            MAX-ACCESS read-only
            STATUS current
            DESCRIPTION
                "The bandwidth of Class-Type 1 (CT1) in this tunnel, in kbit/s.
                Unit: kbit/s"
            ::= { hwMplsTunnelEntry 21 }

        
        hwMplsTunnelCt2Bandwidth OBJECT-TYPE
            SYNTAX Unsigned32
            UNITS "kilobits per second"
            MAX-ACCESS read-only
            STATUS current
            DESCRIPTION
                "The bandwidth of Class-Type 2 (CT2) in this tunnel, in kbit/s.
                Unit: kbit/s"
            ::= { hwMplsTunnelEntry 22 }

        
        hwMplsTunnelCt3Bandwidth OBJECT-TYPE
            SYNTAX Unsigned32
            UNITS "kilobits per second"
            MAX-ACCESS read-only
            STATUS current
            DESCRIPTION
                "The bandwidth of Class-Type 3 (CT3) in this tunnel, in kbit/s.
                Unit: kbit/s"
            ::= { hwMplsTunnelEntry 23 }

        
        hwMplsTunnelCt4Bandwidth OBJECT-TYPE
            SYNTAX Unsigned32
            UNITS "kilobits per second"
            MAX-ACCESS read-only
            STATUS current
            DESCRIPTION
                "The bandwidth of Class-Type 4 (CT4) in this tunnel, in kbit/s.
                Unit: kbit/s"
            ::= { hwMplsTunnelEntry 24 }

        
        hwMplsTunnelCt5Bandwidth OBJECT-TYPE
            SYNTAX Unsigned32
            UNITS "kilobits per second"
            MAX-ACCESS read-only
            STATUS current
            DESCRIPTION
                "The bandwidth of Class-Type 5 (CT5) in this tunnel, in kbit/s.
                Unit: kbit/s"
            ::= { hwMplsTunnelEntry 25 }

        
        hwMplsTunnelCt6Bandwidth OBJECT-TYPE
            SYNTAX Unsigned32
            UNITS "kilobits per second"
            MAX-ACCESS read-only
            STATUS current
            DESCRIPTION
                "The bandwidth of Class-Type 6 (CT6) in this tunnel, in kbit/s.
                Unit: kbit/s"
            ::= { hwMplsTunnelEntry 26 }

        
        hwMplsTunnelCt7Bandwidth OBJECT-TYPE
            SYNTAX Unsigned32
            UNITS "kilobits per second"
            MAX-ACCESS read-only
            STATUS current
            DESCRIPTION
                "The bandwidth of Class-Type 7 (CT7) in this tunnel, in kbit/s.
                Unit: kbit/s"
            ::= { hwMplsTunnelEntry 27 }

        hwMplsTunnelLspType OBJECT-TYPE
            SYNTAX INTEGER
            {
            invalid(0),
            primary(1),
            primary-modifing(2),
            hot-standby(3),
            hot-standby-modifing(4),
            ordinary(5),
            ordinary-modifing(6),
            best-effort(7),
            best-effort-modifing(8)
            }
            
            MAX-ACCESS read-only
            STATUS current
            DESCRIPTION
                "1. This object is meaningful only at the ingress of the tunnel.
                 2. It indicates LSP types:
                 (0) Invalid LSP: indicates that the LSP type is invalid. The possible cause is that the LSP is not created at an ingress.
                 (1) Primary LSP: indicates the primary LSP.
                 (2) Primary modifing LSP: indicates the LSP that will replace the primary LSP.
                 (3) Hot-standby LSP: indicates the hot-standby LSP.
                 (4) Hot-standby modifing LSP: indicates the LSP that will replace the hot-standby LSP.
                 (5) Ordinary LSP: indicates the ordinary LSP.                
                 (6) Ordinary modifying LSP: indicates the LSP that will replace the ordinary LSP.      
                 (7) Best-effort LSP: indicates the Best-Effort LSP.            
                 (8) Best-effort modifing LSP: indicates the LSP that will replace the Best-Effort LSP.  
                 3. Modifying LSPs are created when users modify the make-before-break attribute of the corresponding LSP types. After being created, modifying LSPs replace the corresponding LSPs to transmit traffic.
                 Default : invalid(0)
                "
            ::= { hwMplsTunnelEntry 28 }

        hwMplsTunnelInterfaceName OBJECT-TYPE
            SYNTAX SnmpAdminString
            MAX-ACCESS read-only
            STATUS current
            DESCRIPTION
                "Indicates the tunnel interface name. The object is 
                only valid at the ingress."
            ::= { hwMplsTunnelEntry 29 }
                 
--   1.3.6.1.4.1.2011.5.25.121.1.1.1.30
        hwMplsTunnelSignalProto OBJECT-TYPE
            SYNTAX INTEGER
                {
                rsvpTE(1),
                static(2),
                staticCR(3)
                }
            MAX-ACCESS read-only
            STATUS current
            DESCRIPTION
                "Indicates the signal protocol of this tunnel"
            ::= { hwMplsTunnelEntry 30 }


--   1.3.6.1.4.1.2011.5.25.121.1.2
        hwTunnelFrrBypassTable OBJECT-TYPE
            SYNTAX SEQUENCE OF HwTunnelFrrBypassEntry
            MAX-ACCESS not-accessible
            STATUS current
            DESCRIPTION
                "Indicates the bypass tunnel. The indexes of this table are 
                hwTunnelFrrBypassListIndex and hwTunnelFrrBypassIndex."
            ::= { hwMplsExtendMibTunnel 2 }

        
--    1.3.6.1.4.1.2011.5.25.121.1.2.1
        hwTunnelFrrBypassEntry OBJECT-TYPE
            SYNTAX HwTunnelFrrBypassEntry
            MAX-ACCESS not-accessible
            STATUS current
            DESCRIPTION
                "Indicates the bypass tunnel.The indexes of this entry are 
                hwTunnelFrrBypassListIndex and hwTunnelFrrBypassIndex."
            INDEX { hwTunnelFrrBypassListIndex, hwTunnelFrrBypassIndex }
            ::= { hwTunnelFrrBypassTable 1 }

        
        HwTunnelFrrBypassEntry ::=
            SEQUENCE { 
                hwTunnelFrrBypassListIndex
                    Unsigned32,
                hwTunnelFrrBypassIndex
                    Unsigned32,
                hwTunnelFrrBypassProtIfIndex
                    Unsigned32
             }

--    1.3.6.1.4.1.2011.5.25.121.1.2.1.1
        hwTunnelFrrBypassListIndex OBJECT-TYPE
            SYNTAX Unsigned32
            MAX-ACCESS not-accessible
            STATUS current
            DESCRIPTION
                "Indicates the index of the bypass tunnel table, that is, the LSP ID of the bypass tunnel."
            ::= { hwTunnelFrrBypassEntry 1 }

        
--    1.3.6.1.4.1.2011.5.25.121.1.2.1.2
        hwTunnelFrrBypassIndex OBJECT-TYPE
            SYNTAX Unsigned32
            MAX-ACCESS not-accessible
            STATUS current
            DESCRIPTION
                "Indicates the index of the bypass tunnel interface."
            ::= { hwTunnelFrrBypassEntry 2 }

        
--    1.3.6.1.4.1.2011.5.25.121.1.2.1.3
        hwTunnelFrrBypassProtIfIndex OBJECT-TYPE
            SYNTAX Unsigned32
            MAX-ACCESS read-only
            STATUS current
            DESCRIPTION
                "Indicates the index of the interface protected by the bypass tunnel."
            ::= { hwTunnelFrrBypassEntry 3 }

        
--   1.3.6.1.4.1.2011.5.25.121.1.3
        hwTunnelFrrARHopTable OBJECT-TYPE
            SYNTAX SEQUENCE OF HwTunnelFrrARHopEntry
            MAX-ACCESS not-accessible
            STATUS current
            DESCRIPTION
                "Indicates the FrrARHopTable, which will show every hop's frr 
                protect information of the tunnel.
                The indexes of this table are hwTunnelFrrARHopListIndex and hwTunnelFrrARHopIndex."
            ::= { hwMplsExtendMibTunnel 3 }

        
--    1.3.6.1.4.1.2011.5.25.121.1.3.1
        hwTunnelFrrARHopEntry OBJECT-TYPE
            SYNTAX HwTunnelFrrARHopEntry
            MAX-ACCESS not-accessible
            STATUS current
            DESCRIPTION
                "Indicates the FrrARHopTable, which will show every hop's frr 
                protect information of the tunnel.
                The indexes of this entry are hwTunnelFrrARHopListIndex and hwTunnelFrrARHopIndex."
            INDEX { hwTunnelFrrARHopListIndex, hwTunnelFrrARHopIndex }
            ::= { hwTunnelFrrARHopTable 1 }

        
        HwTunnelFrrARHopEntry ::=
            SEQUENCE { 
                hwTunnelFrrARHopListIndex
                    Unsigned32,
                hwTunnelFrrARHopIndex
                    Unsigned32,
                hwTunnelFrrARHopProtDesired
                    BITS,
                hwTunnelFrrARHopProtActual
                    BITS
             }

--    1.3.6.1.4.1.2011.5.25.121.1.3.1.1
        hwTunnelFrrARHopListIndex OBJECT-TYPE
            SYNTAX Unsigned32
            MAX-ACCESS not-accessible
            STATUS current
            DESCRIPTION
                "Indicates the table index of each hop along the primary tunnel."
            ::= { hwTunnelFrrARHopEntry 1 }

        
--    1.3.6.1.4.1.2011.5.25.121.1.3.1.2
        hwTunnelFrrARHopIndex OBJECT-TYPE
            SYNTAX Unsigned32
            MAX-ACCESS not-accessible
            STATUS current
            DESCRIPTION
                "Indicates the index of each hop along the primary tunnel."
            ::= { hwTunnelFrrARHopEntry 2 }

        
--    1.3.6.1.4.1.2011.5.25.121.1.3.1.3
        hwTunnelFrrARHopProtDesired OBJECT-TYPE
            SYNTAX BITS
                {
                localProtection(0),
                nodeProtection(1),
                bandwidthProtection(2)
                }
            MAX-ACCESS read-only
            STATUS current
            DESCRIPTION
                "Indicates the FRR protection types desired by the primary tunnel interface, including:
                0: link protection,
                1: node protection,
                2: bandwidth protection
                "
            ::= { hwTunnelFrrARHopEntry 3 }

        
--    1.3.6.1.4.1.2011.5.25.121.1.3.1.4
        hwTunnelFrrARHopProtActual OBJECT-TYPE
            SYNTAX BITS
                {
                localProtection(0),
                nodeProtection(1),
                bandwidthProtection(2),
                protectionInuse(3)
                }
            MAX-ACCESS read-only
            STATUS current
            DESCRIPTION
                "Indicates the actual FRR protection types of the primary tunnel interface, including:
                0: link protection,
                1: node protection,
                2: bandwidth protection,
                3: primary tunnel protection in use
                "
            ::= { hwTunnelFrrARHopEntry 4 }

        
--   1.3.6.1.4.1.2011.5.25.121.1.4
        hwTunnelFrrRouteDBTable OBJECT-TYPE
            SYNTAX SEQUENCE OF HwTunnelFrrRouteDBEntry
            MAX-ACCESS not-accessible
            STATUS current
            DESCRIPTION
                "Indicates the primary tunnel is protected by which bypass tunnel. The indexes of this
                table are hwTunnelFrrRouteDBTunnelIndex, hwTunnelFrrRouteDBTunnelInstance, 
                hwTunnelFrrRouteDBTunnelIngressLSRId and hwTunnelFrrRouteDBTunnelEngressLSRId."
            ::= { hwMplsExtendMibTunnel 4 }

        
--    1.3.6.1.4.1.2011.5.25.121.1.4.1
        hwTunnelFrrRouteDBEntry OBJECT-TYPE
            SYNTAX HwTunnelFrrRouteDBEntry
            MAX-ACCESS not-accessible
            STATUS current
            DESCRIPTION
                "Indicates the primary tunnel is protected by which bypass tunnel. The indexes of this
                entry are hwTunnelFrrRouteDBTunnelIndex, hwTunnelFrrRouteDBTunnelInstance, 
                hwTunnelFrrRouteDBTunnelIngressLSRId and hwTunnelFrrRouteDBTunnelEngressLSRId."
            INDEX { hwTunnelFrrRouteDBTunnelIndex, hwTunnelFrrRouteDBTunnelInstance, hwTunnelFrrRouteDBTunnelIngressLSRId, hwTunnelFrrRouteDBTunnelEngressLSRId }
            ::= { hwTunnelFrrRouteDBTable 1 }

        
        HwTunnelFrrRouteDBEntry ::=
            SEQUENCE { 
                hwTunnelFrrRouteDBTunnelIndex
                    Unsigned32,
                hwTunnelFrrRouteDBTunnelInstance
                    Unsigned32,
                hwTunnelFrrRouteDBTunnelIngressLSRId
                    Unsigned32,
                hwTunnelFrrRouteDBTunnelEngressLSRId
                    Unsigned32,
                hwTunnelFrrRouteDBBypassIfIndex
                    Unsigned32,
                hwTunnelFrrRouteDBInnerLabel
                    Unsigned32
             }

--    1.3.6.1.4.1.2011.5.25.121.1.4.1.1
        hwTunnelFrrRouteDBTunnelIndex OBJECT-TYPE
            SYNTAX Unsigned32
            MAX-ACCESS not-accessible
            STATUS current
            DESCRIPTION
                "Identifies the index of the primary. Manager obtains new index 
                values for row creation in this table by reading mplsTunnelIndexNext. 
                When the MPLS signaling protocol is rsvp(2), this value equals to 
                the value signaled in the Tunnel ID of the SESSION object. When 
                the MPLS signaling protocol is crldp(3), this value equals to the 
                value signaled in the LSP ID. Reference to MPLS-TE-STD-MIB."
            ::= { hwTunnelFrrRouteDBEntry 1 }

        
--    1.3.6.1.4.1.2011.5.25.121.1.4.1.2
        hwTunnelFrrRouteDBTunnelInstance OBJECT-TYPE
            SYNTAX Unsigned32
            MAX-ACCESS not-accessible
            STATUS current
            DESCRIPTION
                "Uniquely identifies a particular instance of a
                tunnel between a pair of ingress and egress LSRs. 
                It is the object identifies multiple instances of 
                tunnels for the purposes of backup and parallel 
                tunnels. When the MPLS signaling protocol is 
                rsvp(2), this value equals to the LSP ID
                of the Sender Template object. When the signaling
                protocol is crldp(3), there is no equivalent
                signaling object. Reference to MPLS-TE-STD-MIB."
            ::= { hwTunnelFrrRouteDBEntry 2 }

        
--    1.3.6.1.4.1.2011.5.25.121.1.4.1.3
        hwTunnelFrrRouteDBTunnelIngressLSRId OBJECT-TYPE
            SYNTAX Unsigned32
            MAX-ACCESS not-accessible
            STATUS current
            DESCRIPTION
                "Identifies the ingress LSR ID of the primary tunnel. 
                When the MPLS signalling protocol is rsvp(2),LSR ID 
                equals to the Tunnel Sender Address in the Sender 
                Template object or the Extended Tunnel Id in the 
                SESSION object. When the MPLS signalling protocol is 
                crldp(3),  LSR ID equals to the Ingress 
                LSR Router ID in the LSPID TLV object."
            ::= { hwTunnelFrrRouteDBEntry 3 }

        
--    1.3.6.1.4.1.2011.5.25.121.1.4.1.4
        hwTunnelFrrRouteDBTunnelEngressLSRId OBJECT-TYPE
            SYNTAX Unsigned32
            MAX-ACCESS not-accessible
            STATUS current
            DESCRIPTION
                "Identifies the egress LSR ID of the primary tunnel. 
                Reference to MPLS-TE-STD-MIB."
            ::= { hwTunnelFrrRouteDBEntry 4 }

        
--    1.3.6.1.4.1.2011.5.25.121.1.4.1.5
        hwTunnelFrrRouteDBBypassIfIndex OBJECT-TYPE
            SYNTAX Unsigned32
            MAX-ACCESS read-only
            STATUS current
            DESCRIPTION
                "Indicates the interface index of the bypass tunnel."
            ::= { hwTunnelFrrRouteDBEntry 5 }

        
--    1.3.6.1.4.1.2011.5.25.121.1.4.1.6
        hwTunnelFrrRouteDBInnerLabel OBJECT-TYPE
            SYNTAX Unsigned32
            MAX-ACCESS read-only
            STATUS current
            DESCRIPTION
                "Indicates the inner label of the primary tunnel and bypass tunnel."
            ::= { hwTunnelFrrRouteDBEntry 6 }

        
--   1.3.6.1.4.1.2011.5.25.121.1.5
        hwStaticLspTable OBJECT-TYPE
            SYNTAX SEQUENCE OF HwStaticLspEntry
            MAX-ACCESS not-accessible
            STATUS current
            DESCRIPTION
                "A static LSP is created by a network administrator by using 
                static MPLS. Note that only point-to-point static LSP segments
                are supported. Each static MPLS LSP can thus have one out-segment
                originating at this LSR and/or one in-segment terminating at
                this LSR. The indexes of this table are hwStaticLspIndex, 
                hwStaticLspInSegmentIndex, and hwStaticLspOutSegmentIndex."
            ::= { hwMplsExtendMibTunnel 5 }

        
--    1.3.6.1.4.1.2011.5.25.121.1.5.1
        hwStaticLspEntry OBJECT-TYPE
            SYNTAX HwStaticLspEntry
            MAX-ACCESS not-accessible
            STATUS current
            DESCRIPTION
                "A static LSP is created by a network administrator by using 
                static MPLS. Note that only point-to-point static LSP segments
                are supported. Each static MPLS LSP can thus have one out-segment
                originating at this LSR and/or one in-segment terminating at
                this LSR. The indexes of this entry are hwStaticLspIndex, 
                hwStaticLspInSegmentIndex, and hwStaticLspOutSegmentIndex."
            INDEX { hwStaticLspIndex, hwStaticLspInSegmentIndex, hwStaticLspOutSegmentIndex }
            ::= { hwStaticLspTable 1 }

        
        HwStaticLspEntry ::=
            SEQUENCE { 
                hwStaticLspIndex
                    MplsIndexType,
                hwStaticLspInSegmentIndex
                    MplsIndexType,
                hwStaticLspOutSegmentIndex
                    MplsIndexType,
                hwStaticLspOwner
                    INTEGER,
                hwStaticLspName
                    SnmpAdminString,
                hwStaticLspStatus
                    INTEGER,
                hwStaticLspClassType
                    INTEGER,
                hwStaticLspBandwidth
                    Unsigned32
             }

--    1.3.6.1.4.1.2011.5.25.121.1.5.1.1
        hwStaticLspIndex OBJECT-TYPE
            SYNTAX MplsIndexType
            MAX-ACCESS not-accessible
            STATUS current
            DESCRIPTION
                "Indicates the index of the static LSP. If the string is 0x00, 
                it means that the index is invalid."
            ::= { hwStaticLspEntry 1 }

        
--    1.3.6.1.4.1.2011.5.25.121.1.5.1.2
        hwStaticLspInSegmentIndex OBJECT-TYPE
            SYNTAX MplsIndexType
            MAX-ACCESS not-accessible
            STATUS current
            DESCRIPTION
                "Indicates the incoming label index of the static LSP/CR-LSP. 
                If the string is 0x00, it means that the index is invalid. 
                In this case, no corresponding mplsInSegmentEntry exists. 
                Reference to MPLS-LSR-STD-MIB."
            ::= { hwStaticLspEntry 2 }

        
--    1.3.6.1.4.1.2011.5.25.121.1.5.1.3
        hwStaticLspOutSegmentIndex OBJECT-TYPE
            SYNTAX MplsIndexType
            MAX-ACCESS not-accessible
            STATUS current
            DESCRIPTION
                "Indicates the outgoing index of the static LSP/CR-LSP. 
                If the entry is used to identify the incoming node or 
                intermediate node of the LSP, this object cannot be set 
                to the string 0x00. Because corresponding mplsOutSegmentEntry 
                exists. If the entry is used to identify the outgoing node 
                of the LSP, this object must be set to the string 0x00. Because  
                no corresponding mplsOutSegmentEntry exists. 
                Reference to MPLS-LSR-STD-MIB."
            ::= { hwStaticLspEntry 3 }

        
--    1.3.6.1.4.1.2011.5.25.121.1.5.1.4
        hwStaticLspOwner OBJECT-TYPE
            SYNTAX INTEGER
                {
                static(1),
                crstatic(2),
                other(3)
                }
            MAX-ACCESS read-only
            STATUS current
            DESCRIPTION
                "Denotes the entity that creates and manages the static LSP. See MPLS-LSR-STD-MIB.
                Options:
                1. static(1)          -indicates the static LSP. 
                2. crstatic(2)        -indicates the static CR-LSP. 
                3. other(3)           -indicates the LSP of another type.
                "
            ::= { hwStaticLspEntry 4 }

        
--    1.3.6.1.4.1.2011.5.25.121.1.5.1.5
        hwStaticLspName OBJECT-TYPE
            SYNTAX SnmpAdminString
            MAX-ACCESS read-only
            STATUS current
            DESCRIPTION
                "Indicates the name of the static LSP or CR-LSP. 
                The name is appointed when the static LSP or CR-LSP 
                is created."
            REFERENCE
                "RFC 2863 - The Interfaces Group MIB, McCloghrie, K.,
                and F. Kastenholtz, June 2000"
            ::= { hwStaticLspEntry 5 }

        
--    1.3.6.1.4.1.2011.5.25.121.1.5.1.6
        hwStaticLspStatus OBJECT-TYPE
            SYNTAX INTEGER
                {
                up(1),
                down(2),
                testing(3)
                }
            MAX-ACCESS read-only
            STATUS current
            DESCRIPTION
                "Indicates the actual operation status of the static LSP/CR-LSP. 
                Options: 
                1. up(1)        -indicates that the static LSP/CR-LSP is in Up state.
                2. down(2)      -indicates that the static LSP/CR-LSP is in down state.
                3. testing(3)   -indicates that the static LSP/CR-LSP is used in test mode.
                "
            ::= { hwStaticLspEntry 6 }

        
        hwStaticLspClassType OBJECT-TYPE
            SYNTAX INTEGER
                {
                ct0(1),
                ct1(2),
                ct2(3),
                ct3(4),
                ct4(5),
                ct5(6),
                ct6(7),
                ct7(8)
                }
            MAX-ACCESS read-only
            STATUS current
            DESCRIPTION
                "The Class-Type of this static lsp.
                Options:                                                         
                1. ct0(1)   -indicates that the class type of static CR-LSP is ct0. 
                2. ct1(2)   -indicates that the class type of static CR-LSP is ct1.
                3. ct2(3)   -indicates that the class type of static CR-LSP is ct2.
                4. ct3(4)   -indicates that the class type of static CR-LSP is ct3.
                5. ct4(5)   -indicates that the class type of static CR-LSP is ct4.
                6. ct5(6)   -indicates that the class type of static CR-LSP is ct5.
                7. ct6(7)   -indicates that the class type of static CR-LSP is ct6.
                8. ct7(8)   -indicates that the class type of static CR-LSP is ct7.              
                "        
            ::= { hwStaticLspEntry 7 }
                         
                         
        hwStaticLspBandwidth OBJECT-TYPE
            SYNTAX Unsigned32
            UNITS "kilobits per second"
            MAX-ACCESS read-only
            STATUS current
            DESCRIPTION
                "The bandwidth of this static lsp.
                Unit: kbit/s"
            ::= { hwStaticLspEntry 8 }

        
        hwMplsTeClassTable OBJECT-TYPE
            SYNTAX SEQUENCE OF HwMplsTeClassEntry
            MAX-ACCESS not-accessible
            STATUS current
            DESCRIPTION
                "TE-class mapping is a set of a maximum of eight TE-class items.          
                TE-class is a <Class-Type, Priority> pair, such as TE-Class[1] = <CT0, 5>.              
                A (setup/holding) priority associated with an LSP valid only if it appears
                as a pair with the Class-Type. Class-Types and priorities can be randomly
                paired up. You can define a maximum of eight <Class-Type, Priority> pairs.     
                The LSR is considered to support a particular Class-Type only if it appears 
                in the definition of the eight possible TE-Classes. It is suggested that all
                the LSRs in the domain use the same TE-Class mapping. The index of this table
                is hwMplsTeClassId."
            ::= { hwMplsExtendMibTunnel 6 }

        
        hwMplsTeClassEntry OBJECT-TYPE
            SYNTAX HwMplsTeClassEntry
            MAX-ACCESS not-accessible
            STATUS current
            DESCRIPTION
                "TE-class mapping is a set of a maximum of eight TE-class items.          
                TE-class is a <Class-Type, Priority> pair, such as TE-Class[1] = <CT0, 5>.              
                A (setup/holding) priority associated with an LSP valid only if it appears
                as a pair with the Class-Type. Class-Types and priorities can be randomly
                paired up. You can define a maximum of eight <Class-Type, Priority> pairs.     
                The LSR is considered to support a particular Class-Type only if it appears 
                in the definition of the eight possible TE-Classes. It is suggested that all
                the LSRs in the domain use the same TE-Class mapping. The index of this entry
                is hwMplsTeClassId."
            INDEX { hwMplsTeClassId }
            ::= { hwMplsTeClassTable 1 }

        
        HwMplsTeClassEntry ::=
            SEQUENCE { 
                hwMplsTeClassId
                    Unsigned32,
                hwMplsTeClassClassType
                    INTEGER,
                hwMplsTeClassPriority
                    Unsigned32,
                hwMplsTeClassDescription
                    OCTET STRING
             }

        hwMplsTeClassId OBJECT-TYPE
            SYNTAX Unsigned32
            MAX-ACCESS not-accessible
            STATUS current
            DESCRIPTION
                "This value represents the index of the TE-Class configured
                on this LSR."
            ::= { hwMplsTeClassEntry 1 }

        
        hwMplsTeClassClassType OBJECT-TYPE
            SYNTAX INTEGER
                {
                ct0(1),
                ct1(2),
                ct2(3),
                ct3(4),
                ct4(5),
                ct5(6),
                ct6(7),
                ct7(8)
                }
            MAX-ACCESS read-only
            STATUS current
            DESCRIPTION
                "This value represents a Class-Type supported on the LSR.
                Options:                                                          
                1. ct0(1)   -indicates that the class type of static CR-LSP is ct0.
                2. ct1(2)   -indicates that the class type of static CR-LSP is ct1.
                3. ct2(3)   -indicates that the class type of static CR-LSP is ct2.
                4. ct3(4)   -indicates that the class type of static CR-LSP is ct3.
                5. ct4(5)   -indicates that the class type of static CR-LSP is ct4.
                6. ct5(6)   -indicates that the class type of static CR-LSP is ct5.
                7. ct6(7)   -indicates that the class type of static CR-LSP is ct6.
                8. ct7(8)   -indicates that the class type of static CR-LSP is ct7.
                "
            ::= { hwMplsTeClassEntry 2 }

        
        hwMplsTeClassPriority OBJECT-TYPE
            SYNTAX Unsigned32
            MAX-ACCESS read-only
            STATUS current
            DESCRIPTION
                "This value represents the preemption priority (setup or holding) 
                supported for a particular class-type, on the LSR.
                Range: 0-7
                Default: 7
                "
            ::= { hwMplsTeClassEntry 3 }

        
        hwMplsTeClassDescription OBJECT-TYPE
            SYNTAX OCTET STRING
            MAX-ACCESS read-only
            STATUS current
            DESCRIPTION
                "Textual description of the TE-Class defined by this row."
            ::= { hwMplsTeClassEntry 4 }

        
        hwMplsIfBcTable OBJECT-TYPE
            SYNTAX SEQUENCE OF HwMplsIfBcEntry
            MAX-ACCESS not-accessible
            STATUS current
            DESCRIPTION
                "This table describes bandwidth constraints associated with MPLS TE
                enabled interfaces. The index of this table is ifIndex."
            ::= { hwMplsExtendMibTunnel 7 }

        
        hwMplsIfBcEntry OBJECT-TYPE
            SYNTAX HwMplsIfBcEntry
            MAX-ACCESS not-accessible
            STATUS current
            DESCRIPTION
                "This table describes bandwidth constraints associated with MPLS TE
                enabled interfaces. The index of this entry is ifIndex."
            INDEX { ifIndex }
            ::= { hwMplsIfBcTable 1 }

        
        HwMplsIfBcEntry ::=
            SEQUENCE { 
                hwMplsIfMaxResvBandwidth
                    Unsigned32,
                hwMplsIfBc0Bandwidth
                    Unsigned32,
                hwMplsIfBc1Bandwidth
                    Unsigned32,
                hwMplsIfBc2Bandwidth
                    Unsigned32,
                hwMplsIfBc3Bandwidth
                    Unsigned32,
                hwMplsIfBc4Bandwidth
                    Unsigned32,
                hwMplsIfBc5Bandwidth
                    Unsigned32,
                hwMplsIfBc6Bandwidth
                    Unsigned32,
                hwMplsIfBc7Bandwidth
                    Unsigned32
             }

        hwMplsIfMaxResvBandwidth OBJECT-TYPE
            SYNTAX Unsigned32
            UNITS "kilobits per second"
            MAX-ACCESS read-only
            STATUS current
            DESCRIPTION
                "The maximum reservable bandwidth on this interface.
                Unit: kbit/s 
                "
            ::= { hwMplsIfBcEntry 1 }

        
        hwMplsIfBc0Bandwidth OBJECT-TYPE
            SYNTAX Unsigned32
            UNITS "kilobits per second"
            MAX-ACCESS read-only
            STATUS current
            DESCRIPTION
                "The bandwidth of Class-Type 0 (CT0) in this tunnel.
                Unit: kbit/s
                "
            ::= { hwMplsIfBcEntry 2 }

        
        
        hwMplsIfBc1Bandwidth OBJECT-TYPE
            SYNTAX Unsigned32
            UNITS "kilobits per second"
            MAX-ACCESS read-only
            STATUS current
            DESCRIPTION
                "The bandwidth of Class-Type 1 (CT1) in this tunnel.
                Unit: kbit/s
                "
            ::= { hwMplsIfBcEntry 3 }

        
        hwMplsIfBc2Bandwidth OBJECT-TYPE
            SYNTAX Unsigned32
            UNITS "kilobits per second"
            MAX-ACCESS read-only
            STATUS current
            DESCRIPTION
                "The bandwidth of Class-Type 2 (CT2) in this tunnel.
                Unit: kbit/s
                "
            ::= { hwMplsIfBcEntry 4 }

        
        hwMplsIfBc3Bandwidth OBJECT-TYPE
            SYNTAX Unsigned32
            UNITS "kilobits per second"
            MAX-ACCESS read-only
            STATUS current
            DESCRIPTION
                "The bandwidth of Class-Type 3 (CT3) in this tunnel.
                Unit: kbit/s
                "
            ::= { hwMplsIfBcEntry 5 }

        
        hwMplsIfBc4Bandwidth OBJECT-TYPE
            SYNTAX Unsigned32
            UNITS "kilobits per second"
            MAX-ACCESS read-only
            STATUS current
            DESCRIPTION
                "The bandwidth of Class-Type 4 (CT4) in this tunnel.
                Unit: kbit/s
                "
            ::= { hwMplsIfBcEntry 6 }

        
        hwMplsIfBc5Bandwidth OBJECT-TYPE
            SYNTAX Unsigned32
            UNITS "kilobits per second"
            MAX-ACCESS read-only
            STATUS current
            DESCRIPTION
                "The bandwidth of Class-Type 5 (CT5) in this tunnel.
                Unit: kbit/s
                "
            ::= { hwMplsIfBcEntry 7 }

        
        hwMplsIfBc6Bandwidth OBJECT-TYPE
            SYNTAX Unsigned32
            UNITS "kilobits per second"
            MAX-ACCESS read-only
            STATUS current
            DESCRIPTION
                "The bandwidth of Class-Type 6 (CT6) in this tunnel.
                Unit: kbit/s
                "
            ::= { hwMplsIfBcEntry 8 }
                
        
        hwMplsIfBc7Bandwidth OBJECT-TYPE
            SYNTAX Unsigned32
            UNITS "kilobits per second"
            MAX-ACCESS read-only
            STATUS current
            DESCRIPTION
                "The bandwidth of Class-Type 7 (CT7) in this tunnel.
                Unit: kbit/s
                "               
            ::= { hwMplsIfBcEntry 9 }
        
        hwStaticLspTnlTable OBJECT-TYPE
            SYNTAX SEQUENCE OF HwStaticLspTnlEntry
            MAX-ACCESS not-accessible
            STATUS current
            DESCRIPTION
                "hwStaticLspTnlTable is used to display static LSP token of   
                 a static LSP of a specified name. The index of this table 
                 is hwStaticLspTnlName."
            ::= { hwMplsExtendMibTunnel 8 }
        
        hwStaticLspTnlEntry OBJECT-TYPE
            SYNTAX HwStaticLspTnlEntry
            MAX-ACCESS not-accessible
            STATUS current
            DESCRIPTION
                "hwStaticLspTnlTable is used to display static LSP token of   
                 a static LSP of a specified name. The index of this entry 
                 is hwStaticLspTnlName."
            INDEX { hwStaticLspTnlName }
            ::= { hwStaticLspTnlTable 1 }
        
        HwStaticLspTnlEntry ::=
            SEQUENCE { 
                hwStaticLspTnlName
                    SnmpAdminString,
                hwStaticLspTnlToken
                    Unsigned32
             }

        hwStaticLspTnlName OBJECT-TYPE
            SYNTAX SnmpAdminString
            MAX-ACCESS not-accessible
            STATUS current
            DESCRIPTION
                "Indicates the name of the Static Lsp."
            ::= { hwStaticLspTnlEntry 1 }
        
        hwStaticLspTnlToken OBJECT-TYPE
            SYNTAX Unsigned32
            MAX-ACCESS read-only
            STATUS current
            DESCRIPTION
                "Indicates the token of the Static Lsp."
            ::= { hwStaticLspTnlEntry 2 }
        
        hwMplsTeVpnQosTable OBJECT-TYPE
            SYNTAX SEQUENCE OF HwMplsTeVpnQosEntry
            MAX-ACCESS not-accessible
            STATUS current
            DESCRIPTION
                "This table is used to display VPN QoS information of a specified TE Tunnel according to TunnelID.
                 The index of this table is hwMplsTnlID."
            ::= { hwMplsExtendMibTunnel 9 }
            
        hwMplsTeVpnQosEntry OBJECT-TYPE
            SYNTAX HwMplsTeVpnQosEntry
            MAX-ACCESS not-accessible
            STATUS current
            DESCRIPTION
                "This table is used to display VPN QoS information of a specified TE Tunnel according to TunnelID.
                 The index of this entry is hwMplsTnlID."
            INDEX { hwMplsTnlID }
            ::= { hwMplsTeVpnQosTable 1 } 
            
        HwMplsTeVpnQosEntry ::=
             SEQUENCE { 
                hwMplsTnlID
                    Unsigned32,             
                hwMplsTeVpnMaxBandwidth
                    Unsigned32,
                hwMplsTeVpnAllocatedBandwidth
                    Unsigned32
             }
             
        hwMplsTnlID OBJECT-TYPE
            SYNTAX Unsigned32
            MAX-ACCESS not-accessible
            STATUS current
            DESCRIPTION
                "The value of this object identifies the TE tunnel ID."
            ::= { hwMplsTeVpnQosEntry 1 } 
            
       hwMplsTeVpnMaxBandwidth OBJECT-TYPE
            SYNTAX Unsigned32
            MAX-ACCESS read-only
            STATUS current
            DESCRIPTION
                "The value of this object identifies the bandwidth the TE tunnel can provide for VPN QoS.
                Unit: kbit/s"
            ::= { hwMplsTeVpnQosEntry 2 }         
                    
       hwMplsTeVpnAllocatedBandwidth OBJECT-TYPE
            SYNTAX Unsigned32
            MAX-ACCESS read-only
            STATUS current
            DESCRIPTION
                "The value of this object identifies the bandwidth used by VPN QoS, in Kbps.
                Unit: kbit/s"
            ::= { hwMplsTeVpnQosEntry 3 }

       hwStaticLspInIfIndex OBJECT-TYPE
            SYNTAX OCTET STRING
            MAX-ACCESS accessible-for-notify
            STATUS current
            DESCRIPTION
                "Indicates the inbound interface index of a static LSP/CR-LSP."
            ::= { hwMplsExtendMibTunnel 11 }

        -- 1.3.6.1.4.1.2011.5.25.121.1.12
        hwStaticLspInIfName OBJECT-TYPE
            SYNTAX OCTET STRING
            MAX-ACCESS accessible-for-notify
            STATUS current
            DESCRIPTION
                "Indicates the name of an inbound interface of a static LSP/CR-LSP."
            ::= { hwMplsExtendMibTunnel 12 }

        -- 1.3.6.1.4.1.2011.5.25.121.1.13
        hwStaticLspDownReason OBJECT-TYPE
            SYNTAX Integer32
            MAX-ACCESS accessible-for-notify
            STATUS current
            DESCRIPTION
                "Indicates the reason for static LSP/CR-LSP Down:
                0. Other
                1. Static LSP/CR-LSP up
                2. MPLS disabled on an interface
                3. MPLS TE disabled on an interface
                4. Route change
                5. Tunnel binding associated with the static LSP/CR-LSP deleted
                6. Static LSP/CR-LSP configuration delete
                7. Inbound interface Down
                8. Outbound interface Down."                
            ::= { hwMplsExtendMibTunnel 13 }
                                                           
--   1.3.6.1.4.1.2011.5.25.121.2
        hwMplsExtendTrap OBJECT IDENTIFIER ::= { hwMplsExtendMib 2 }

        
--   1.3.6.1.4.1.2011.5.25.121.2.1
        hwLspTrap OBJECT IDENTIFIER ::= { hwMplsExtendTrap 1 }

        
--   1.3.6.1.4.1.2011.5.25.121.2.1.1
        hwMplsStaticLspUp NOTIFICATION-TYPE
            OBJECTS { hwStaticLspName, hwStaticLspStatus, ifName, hwStaticLspInIfIndex, hwStaticLspInIfName, hwStaticLspDownReason }
            STATUS current
            DESCRIPTION 
                "This notification indicates that the status of referred static LSP changes to Up."
            ::= { hwLspTrap 1 }

        
--   1.3.6.1.4.1.2011.5.25.121.2.1.2
        hwMplsStaticLspDown NOTIFICATION-TYPE
            OBJECTS { hwStaticLspName, hwStaticLspStatus, ifName, hwStaticLspInIfIndex, hwStaticLspInIfName, hwStaticLspDownReason }
            STATUS current
            DESCRIPTION 
                "This notification indicates that the status of referred static LSP changes to Down."
            ::= { hwLspTrap 2 }

        
--   1.3.6.1.4.1.2011.5.25.121.2.1.3
        hwMplsStaticCRLspUp NOTIFICATION-TYPE
            OBJECTS { hwStaticLspName, hwStaticLspStatus, ifName, hwStaticLspInIfIndex, hwStaticLspInIfName, hwStaticLspDownReason }
            STATUS current
            DESCRIPTION 
                "This notification indicates that the status of referred static CR-LSP changes to Up."
            ::= { hwLspTrap 3 }

        
--   1.3.6.1.4.1.2011.5.25.121.2.1.4
        hwMplsStaticCRLspDown NOTIFICATION-TYPE
            OBJECTS { hwStaticLspName, hwStaticLspStatus, ifName, hwStaticLspInIfIndex, hwStaticLspInIfName, hwStaticLspDownReason }
            STATUS current
            DESCRIPTION 
                "This notification indicates that the status of referred static CR-LSP changes to Down."
            ::= { hwLspTrap 4 }

        
--   1.3.6.1.4.1.2011.5.25.121.2.1.5
        hwMplsTeFrrProtAval NOTIFICATION-TYPE
            OBJECTS { hwTunnelFrrRouteDBBypassIfIndex, hwTunnelFrrRouteDBInnerLabel }
            STATUS current
            DESCRIPTION 
                "This notification indicates that the primary tunnel is bound to bypass tunnel."
            ::= { hwLspTrap 5 }

        
--   1.3.6.1.4.1.2011.5.25.121.2.1.6
        hwMplsTeFrrProtNotAval NOTIFICATION-TYPE
            OBJECTS { hwTunnelFrrRouteDBBypassIfIndex }
            STATUS current
            DESCRIPTION 
                "This notification indicates that the primary tunnel is unbound to bypass tunnel."
            ::= { hwLspTrap 6 }

        
--   1.3.6.1.4.1.2011.5.25.121.2.1.7
        hwMplsTeFrrSwitch NOTIFICATION-TYPE
            OBJECTS { hwMplsTunnelAdminStatus, hwMplsTunnelOperStatus }
            STATUS current
            DESCRIPTION 
                "This notification indicates that the primary tunnel is switches to the bypass tunnel."
            ::= { hwLspTrap 7 }

        
--   1.3.6.1.4.1.2011.5.25.121.2.1.8
        hwMplsTeFrrResume NOTIFICATION-TYPE
            OBJECTS { hwMplsTunnelAdminStatus, hwMplsTunnelOperStatus }
            STATUS current
            DESCRIPTION 
                "This notification indicates that the primary tunnel is switched back from the bypass tunnel."
            ::= { hwLspTrap 8 }

        
--   1.3.6.1.4.1.2011.5.25.121.2.1.9
        hwMplsTunnelHSBSwitch NOTIFICATION-TYPE
            OBJECTS { hwMplsTunnelAdminStatus, hwMplsTunnelOperStatus }
            STATUS current
            DESCRIPTION 
                "This notification indicates that the data is switched from the primary CR-LSP to the HSB CR-LSP."
            ::= { hwLspTrap 9 }

        
--   1.3.6.1.4.1.2011.5.25.121.2.1.10
        hwMplsTunnelHSBResume NOTIFICATION-TYPE
            OBJECTS { hwMplsTunnelAdminStatus, hwMplsTunnelOperStatus }
            STATUS current
            DESCRIPTION 
                "This notification indicates that the data is switched from the HSB CR-LSP to the primary CR-LSP."
            ::= { hwLspTrap 10 }

        
--   1.3.6.1.4.1.2011.5.25.121.2.1.11
        hwMplsTunnelOBSwitch NOTIFICATION-TYPE
            OBJECTS { hwMplsTunnelAdminStatus, hwMplsTunnelOperStatus }
            STATUS current
            DESCRIPTION 
                "This notification indicates that the primary CR-LSP is down and the Ordinary backup CR-LSP is up."
            ::= { hwLspTrap 11 }

        
--   1.3.6.1.4.1.2011.5.25.121.2.1.12
        hwMplsTunnelOBResume NOTIFICATION-TYPE
            OBJECTS { hwMplsTunnelAdminStatus, hwMplsTunnelOperStatus }
            STATUS current
            DESCRIPTION 
                "This notification indicates that the data is switched from the Ordinary backup CR-LSP to the primary CR-LSP."
            ::= { hwLspTrap 12 }

--   1.3.6.1.4.1.2011.5.25.121.2.1.13
        hwMplsTunnelUp NOTIFICATION-TYPE
            OBJECTS { hwMplsTunnelInterfaceName, hwMplsTunnelAdminStatus, hwMplsTunnelOperStatus }
            STATUS obsolete
            DESCRIPTION 
                "The hwMplsTunnelUp trap indicates that the staus of the tunnel changes into Up."
            ::= { hwLspTrap 13 }

--   1.3.6.1.4.1.2011.5.25.121.2.1.14        
        hwMplsTunnelDown NOTIFICATION-TYPE
            OBJECTS { hwMplsTunnelInterfaceName, hwMplsTunnelAdminStatus, hwMplsTunnelOperStatus }
            STATUS obsolete
            DESCRIPTION 
                "The hwMplsTunnelDown trap indicates that the staus of the tunnel changes into Down."
            ::= { hwLspTrap 14 }

--   1.3.6.1.4.1.2011.5.25.121.2.1.15
        hwMplsTunnelChangeBw NOTIFICATION-TYPE
            OBJECTS { hwMplsTunnelInterfaceName, hwMplsTunnelIfIndex, hwMplsTunnelPreBandwidth, hwMplsTunnelNextBandwidth }
            STATUS current
            DESCRIPTION 
                "This notification indicates that the bandwidth of the tunnel is changed."
            ::= { hwLspTrap 15 }

--   1.3.6.1.4.1.2011.5.25.121.2.1.16
        hwMplsTunnelTpOamLossSD NOTIFICATION-TYPE
            OBJECTS { hwMplsTunnelInterfaceName, hwMplsTunnelSignalProto }
            STATUS current
            DESCRIPTION 
                "This object indicates that the loss ratio of the packets carried by the tunnel exceeded the first threshold."
            ::= { hwLspTrap 16 }

--   1.3.6.1.4.1.2011.5.25.121.2.1.17
        hwMplsOamSDRecovery NOTIFICATION-TYPE
            OBJECTS { hwMplsTunnelInterfaceName, hwMplsTunnelSignalProto  }
            STATUS current
            DESCRIPTION 
                "
                This object indicates that the loss ratio of the packets carried by the tunnel dropped below the first threshold.
                "
            ::= { hwLspTrap 17 } 

--   1.3.6.1.4.1.2011.5.25.121.2.1.18
        hwMplsOamLoss NOTIFICATION-TYPE
            OBJECTS { hwMplsTunnelInterfaceName, hwMplsTunnelSignalProto, ifName}
            STATUS current
            DESCRIPTION 
                "
                This object indicates that TP OAM detected tunnel connectivity faults.
                "
            ::= { hwLspTrap 18 }

--   1.3.6.1.4.1.2011.5.25.121.2.1.19
        hwMplsOamLossRecovery NOTIFICATION-TYPE
            OBJECTS { hwMplsTunnelInterfaceName, hwMplsTunnelSignalProto  }
            STATUS current
            DESCRIPTION 
                "
                This object indicates that TP OAM did not detect tunnel connectivity faults.
                "
            ::= { hwLspTrap 19 }

--   1.3.6.1.4.1.2011.5.25.121.2.1.20
        hwMplsOamAis NOTIFICATION-TYPE
            OBJECTS { hwMplsTunnelInterfaceName, hwMplsTunnelSignalProto  }
            STATUS current
            DESCRIPTION 
                "
                This object indicates that TP OAM detected an alarm indication signal.
                "
            ::= { hwLspTrap 20 }

--   1.3.6.1.4.1.2011.5.25.121.2.1.21
        hwMplsOamAisRecovery NOTIFICATION-TYPE
            OBJECTS { hwMplsTunnelInterfaceName, hwMplsTunnelSignalProto  }
            STATUS current
            DESCRIPTION 
                "
                This object indicates that TP OAM no longer detected alarm indication signals.
                "
            ::= { hwLspTrap 21 }

--   1.3.6.1.4.1.2011.5.25.121.2.1.22
        hwMplsOamRdi NOTIFICATION-TYPE
            OBJECTS { hwMplsTunnelInterfaceName, hwMplsTunnelSignalProto, ifName}
            STATUS current
            DESCRIPTION 
                "
                This object indicates that TP OAM detected remote defects.
                "
            ::= { hwLspTrap 22 }

--   1.3.6.1.4.1.2011.5.25.121.2.1.23
        hwMplsOamRdiRecovery NOTIFICATION-TYPE
            OBJECTS { hwMplsTunnelInterfaceName, hwMplsTunnelSignalProto  }
            STATUS current
            DESCRIPTION 
                "
                This object indicates that the remote defects detected by TP OAM were removed.
                "
            ::= { hwLspTrap 23 }

--   1.3.6.1.4.1.2011.5.25.121.2.1.24
        hwMplsOamMeg NOTIFICATION-TYPE
            OBJECTS { hwMplsTunnelInterfaceName, hwMplsTunnelSignalProto  }
            STATUS current
            DESCRIPTION 
                "
                This object indicates that the names configured on the two ends of the tunnel are inconsistent.
                "
            ::= { hwLspTrap 24 }

--   1.3.6.1.4.1.2011.5.25.121.2.1.25
        hwMplsOamMegRecovery NOTIFICATION-TYPE
            OBJECTS { hwMplsTunnelInterfaceName, hwMplsTunnelSignalProto }
            STATUS current
            DESCRIPTION 
                "
                This object indicates that the names configured on the two ends of the tunnel now are consistent.
                "
            ::= { hwLspTrap 25 }

--   1.3.6.1.4.1.2011.5.25.121.2.1.26
        hwMplsOamMep NOTIFICATION-TYPE
            OBJECTS { hwMplsTunnelInterfaceName, hwMplsTunnelSignalProto }
            STATUS current
            DESCRIPTION 
                "
                This object indicates that the MEP-IDs configured on the two ends of the tunnel are inconsistent.
                "
            ::= { hwLspTrap 26 }

--   1.3.6.1.4.1.2011.5.25.121.2.1.27
        hwMplsOamMepRecovery NOTIFICATION-TYPE
            OBJECTS { hwMplsTunnelInterfaceName, hwMplsTunnelSignalProto }
            STATUS current
            DESCRIPTION 
                "
                This object indicates that the MEP-IDs configured on the two ends of the tunnel now are consistent.
                "
            ::= { hwLspTrap 27 }

--   1.3.6.1.4.1.2011.5.25.121.2.1.28
        hwMplsOamSF NOTIFICATION-TYPE
            OBJECTS { hwMplsTunnelInterfaceName, hwMplsTunnelSignalProto }
            STATUS current
            DESCRIPTION 
                "
                This object indicates that the loss ratio of the packets carried by the tunnel exceeded the second threshold in the local link.
                "
            ::= { hwLspTrap 28 }

--   1.3.6.1.4.1.2011.5.25.121.2.1.29
        hwMplsOamSFRecovery NOTIFICATION-TYPE
            OBJECTS { hwMplsTunnelInterfaceName, hwMplsTunnelSignalProto }
            STATUS current
            DESCRIPTION 
                "
                This object indicates that the loss ratio of the packets carried by the tunnel dropped below the second threshold in the local link.
                "
            ::= { hwLspTrap 29 }

--   1.3.6.1.4.1.2011.5.25.121.2.1.30
        hwMplsOamPeriod NOTIFICATION-TYPE
            OBJECTS { hwMplsTunnelInterfaceName, hwMplsTunnelSignalProto }
            STATUS current
            DESCRIPTION 
                "
                This object indicates that the TP OAM detection periods on the two ends of the tunnel are inconsistent.
                "
            ::= { hwLspTrap 30 }

--   1.3.6.1.4.1.2011.5.25.121.2.1.31
        hwMplsOamPeriodRecovery NOTIFICATION-TYPE
            OBJECTS { hwMplsTunnelInterfaceName, hwMplsTunnelSignalProto }
            STATUS current
            DESCRIPTION 
                "
                This object indicates that the TP OAM detection periods on the two ends of the tunnel now are consistent.
                "
            ::= { hwLspTrap 31 }

--   1.3.6.1.4.1.2011.5.25.121.2.1.32
        hwMplsOamLck NOTIFICATION-TYPE
            OBJECTS { hwMplsTunnelInterfaceName, hwMplsTunnelSignalProto }
            STATUS current
            DESCRIPTION 
                "
                This object indicates that TP OAM detected the remote end of the tunnel has been locked.
                "
            ::= { hwLspTrap 32 }

--   1.3.6.1.4.1.2011.5.25.121.2.1.33
        hwMplsOamLckRecovery NOTIFICATION-TYPE
            OBJECTS { hwMplsTunnelInterfaceName, hwMplsTunnelSignalProto }
            STATUS current
            DESCRIPTION 
                "
                This object indicates that TP OAM detected the remote end of the tunnel has not been locked.
                "
            ::= { hwLspTrap 33 }
                      
--   1.3.6.1.4.1.2011.5.25.121.2.1.34
        hwMplsOamExcess NOTIFICATION-TYPE
            OBJECTS { hwMplsTunnelInterfaceName, hwMplsTunnelSignalProto }
            STATUS current
            DESCRIPTION 
                "
                This object indicates that MPLS OAM detected the tunnel received excess alarm.
                "
            ::= { hwLspTrap 34 } 
            
--   1.3.6.1.4.1.2011.5.25.121.2.1.35
        hwMplsOamExcessRecovery NOTIFICATION-TYPE
            OBJECTS { hwMplsTunnelInterfaceName, hwMplsTunnelSignalProto }
            STATUS current
            DESCRIPTION 
                "
                This object indicates that MPLS OAM detected the tunnel received excess alarm end.
                "
            ::= { hwLspTrap 35 } 
        
--   1.3.6.1.4.1.2011.5.25.121.2.1.36
        hwMplsOamMisMatch NOTIFICATION-TYPE
            OBJECTS { hwMplsTunnelInterfaceName, hwMplsTunnelSignalProto }
            STATUS current
            DESCRIPTION 
                "
                This object indicates that MPLS OAM detected the tunnel received MisMatch alarm.
                "
            ::= { hwLspTrap 36 } 

--   1.3.6.1.4.1.2011.5.25.121.2.1.37
        hwMplsOamMisMatchRecovery NOTIFICATION-TYPE
            OBJECTS { hwMplsTunnelInterfaceName, hwMplsTunnelSignalProto }
            STATUS current
            DESCRIPTION 
                "
                This object indicates that MPLS OAM detected the tunnel received MisMatch alarm end.
                "
            ::= { hwLspTrap 37 } 

--   1.3.6.1.4.1.2011.5.25.121.2.1.38
        hwMplsOamMisMerge NOTIFICATION-TYPE
            OBJECTS { hwMplsTunnelInterfaceName, hwMplsTunnelSignalProto }
            STATUS current
            DESCRIPTION 
                "
                This object indicates that MPLS OAM detected the tunnel received MisMerge alarm.
                "
            ::= { hwLspTrap 38 } 

--   1.3.6.1.4.1.2011.5.25.121.2.1.39
        hwMplsOamMisMergeRecovery NOTIFICATION-TYPE
            OBJECTS { hwMplsTunnelInterfaceName, hwMplsTunnelSignalProto }
            STATUS current
            DESCRIPTION 
                "
                This object indicates that MPLS OAM detected the tunnel received MisMerge alarm end.
                "
            ::= { hwLspTrap 39 } 

--   1.3.6.1.4.1.2011.5.25.121.2.1.40
        hwMplsOamUnknown NOTIFICATION-TYPE
            OBJECTS { hwMplsTunnelInterfaceName, hwMplsTunnelSignalProto }
            STATUS current
            DESCRIPTION 
                "
                This object indicates that MPLS OAM detected the tunnel received Unknown alarm.
                "
            ::= { hwLspTrap 40 } 

--   1.3.6.1.4.1.2011.5.25.121.2.1.41
        hwMplsOamUnknownRecovery NOTIFICATION-TYPE
            OBJECTS { hwMplsTunnelInterfaceName, hwMplsTunnelSignalProto }
            STATUS current
            DESCRIPTION 
                "
                This object indicates that MPLS OAM detected the tunnel received Unknown alarm end.
                "
            ::= { hwLspTrap 41 } 

--   1.3.6.1.4.1.2011.5.25.121.2.1.42
        hwMplsOamBDI NOTIFICATION-TYPE
            OBJECTS { hwMplsTunnelInterfaceName, hwMplsTunnelSignalProto, ifName}
            STATUS current
            DESCRIPTION 
                "
                This object indicates that MPLS OAM detected the tunnel received BDI alarm.
                "
            ::= { hwLspTrap 42 } 

--   1.3.6.1.4.1.2011.5.25.121.2.1.43
        hwMplsOamBDIRecovery NOTIFICATION-TYPE
            OBJECTS { hwMplsTunnelInterfaceName, hwMplsTunnelSignalProto }
            STATUS current
            DESCRIPTION 
                "
                This object indicates that MPLS OAM detected the tunnel received BDI alarm end.
                "
            ::= { hwLspTrap 43 } 

--   1.3.6.1.4.1.2011.5.25.121.2.1.44
        hwMplsOamFail NOTIFICATION-TYPE
            OBJECTS { hwMplsTunnelInterfaceName, hwMplsTunnelSignalProto, ifName}
            STATUS current
            DESCRIPTION 
                "
                This object indicates that MPLS OAM detected the tunnel received OAMFAIL alarm.
                "
            ::= { hwLspTrap 44 } 

--   1.3.6.1.4.1.2011.5.25.121.2.1.45
        hwMplsOamFailRecovery NOTIFICATION-TYPE
            OBJECTS { hwMplsTunnelInterfaceName, hwMplsTunnelSignalProto }
            STATUS current
            DESCRIPTION 
                "
                This object indicates that MPLS OAM detected the tunnel received OAMFAIL alarm end.
                "
            ::= { hwLspTrap 45 } 

--   1.3.6.1.4.1.2011.5.25.121.2.1.46
        hwMplsTunnelPrimaryUp NOTIFICATION-TYPE
            OBJECTS { hwMplsTunnelInterfaceName }
            STATUS current
            DESCRIPTION 
                "This notification indicates that the status of Tunnel Primary LSP changes to Up."
            ::= { hwLspTrap 46 }
            
--   1.3.6.1.4.1.2011.5.25.121.2.1.47
        hwMplsTunnelPrimaryDown NOTIFICATION-TYPE
            OBJECTS { hwMplsTunnelInterfaceName }
            STATUS current
            DESCRIPTION 
                "This notification indicates that the status of Tunnel Primary LSP changes to Down."
            ::= { hwLspTrap 47 }
            
--   1.3.6.1.4.1.2011.5.25.121.2.1.48
        hwMplsTunnelHotstandbyUp NOTIFICATION-TYPE
            OBJECTS { hwMplsTunnelInterfaceName }
            STATUS current
            DESCRIPTION 
                "This notification indicates that the status of Tunnel Hot-standby LSP changes to Up."
            ::= { hwLspTrap 48 }
            
--   1.3.6.1.4.1.2011.5.25.121.2.1.49
        hwMplsTunnelHotstandbyDown NOTIFICATION-TYPE
            OBJECTS { hwMplsTunnelInterfaceName }
            STATUS current
            DESCRIPTION 
                "This notification indicates that the status of Tunnel Hot-standby LSP changes to Down."
            ::= { hwLspTrap 49 }
            
--   1.3.6.1.4.1.2011.5.25.121.2.1.50
        hwMplsTunnelOrdinaryUp NOTIFICATION-TYPE
            OBJECTS { hwMplsTunnelInterfaceName }
            STATUS current
            DESCRIPTION 
                "This notification indicates that the status of Tunnel Ordinary LSP changes to Up."
            ::= { hwLspTrap 50 }
            
--   1.3.6.1.4.1.2011.5.25.121.2.1.51
        hwMplsTunnelOrdinaryDown NOTIFICATION-TYPE
            OBJECTS { hwMplsTunnelInterfaceName }
            STATUS current
            DESCRIPTION 
                "This notification indicates that the status of Tunnel Ordinary LSP changes to Down."
            ::= { hwLspTrap 51 }
            
--   1.3.6.1.4.1.2011.5.25.121.2.1.52
        hwMplsTunnelBesteffortUp NOTIFICATION-TYPE
            OBJECTS { hwMplsTunnelInterfaceName }
            STATUS current
            DESCRIPTION 
                "This notification indicates that the status of Tunnel Best-effort LSP changes to Up."
            ::= { hwLspTrap 52 }
            
--   1.3.6.1.4.1.2011.5.25.121.2.1.53
        hwMplsTunnelBesteffortDown NOTIFICATION-TYPE
            OBJECTS { hwMplsTunnelInterfaceName }
            STATUS current
            DESCRIPTION 
                "This notification indicates that the status of Tunnel Best-effort LSP changes to Down."
            ::= { hwLspTrap 53 }

-- 1.3.6.1.4.1.2011.5.25.121.2.2
        hwMplsTrapObjects OBJECT IDENTIFIER ::= { hwMplsExtendTrap 2 }
        
         hwMplsTunnelIfName OBJECT-TYPE
         SYNTAX           SnmpAdminString
         MAX-ACCESS     accessible-for-notify
         STATUS           obsolete
         DESCRIPTION
             "The Tunnel Interface name."
         ::= { hwMplsTrapObjects 1 }  
             
            
        hwMplsTunnelFrrConfigOper OBJECT-TYPE
        SYNTAX  INTEGER
             {
             unconfig(0),
             config(1),
             unknow(2)
             }
        MAX-ACCESS     accessible-for-notify
        STATUS           obsolete
        DESCRIPTION
            "The value of this object identifies the operation that an FRR configuration is committed on the tunnel.
            Options:                                                       
            1.unconfig(0) -indicates the configuration of the undo mpls te fast-reroute command is committed.  
            2.config(1)   -indicates the configuration of the mpls te fast-reroute command is committed.      
            3.unknow(2)   -indicates an unknown operation."
        ::= { hwMplsTrapObjects 2 }

        hwMplsTunnelDownReason OBJECT-TYPE
            SYNTAX INTEGER
            {
            other(1),
            staticLspDown(2),
            staticCrlspDown(3),
            outIfDown(4),
            resourcePreempted(5),
            rsvpMessageTimeout(6),
            rsvpNeighborLost(7),
            bypassTunnelDownOrUnbinded(8),
            cspfComputeFail(9),
            userShutdown(10),
            tpoamLossOfContinuity(11),
            tpoamAlarmIndicationSignal(12),
            tpoamRemoteDefectIndication(13),
            tpoamUnexpectedMEG(14),
            tpoamUnexpectedMEP(15),
            tpoamLossSF(16),
            tpoamPeriod(17),
            mplsOamLocv(18),
            mplsOamExcess(19),
            mplsOamMisMatch(20),
            mplsOamMisMerge(21),
            mplsOamUnknown(22),
            mplsOamBdi(23),
            mplsOamFdi(24),
            mplsOamSF(25),
            mplsOamSD(26),
            mplsOamDOamFail(27),
            clear(100)
            }
            MAX-ACCESS accessible-for-notify
            STATUS current
            DESCRIPTION
                "Indicates the alarm reason as below:
                1. Other;
                2. Static LSP down;
                3. Static CR-LSP down;
                4. The out interface of the RSVP LSP ingress is down; 
                5. The resource of RSVP LSP is preempted;
                6. RSVP message timeout;
                7. RSVP neighbor lost;
                8. The bypass-tunnel is down or is unbinded with main tunnel, as bypass-tunnel is in used;
                9. CSPF compute fail;
                10.User shutdown the tunnel;
                11.TPOAM indicates the connectivity fault of the link;
                12.TPOAM indicates receive alarm indication signal defect of the link;
                13.TPOAM indicates the remote defect of the link;
                14.TPOAM indicates receive unexpected MEG-ID defect of the link;
                15.TPOAM indicates receive unexpected MEP-ID defect of the link;
                16.TPOAM indicates packet lost exceed signal fault threshold in the local link;
                17.TPOAM indicates packet unexpected period defect of the link;
                18.MPLS OAM connectivity fault;
                19.MPLS OAM TTSI excess;
                20.MPLS OAM TTSI mismatch;
                21.MPLS OAM TTSI merge error;
                22.MPLS OAM unknown error;
                23.MPLS OAM BDI;
                24.MPLS OAM FDI;
                25.MPLS OAM signal fail;
                26.MPLS OAM signal degrade;
                27.MPLS OAM fail;
                100. Clear."
            ::= { hwMplsTrapObjects 3 }

     hwMplsTunnelFrrConfigChange NOTIFICATION-TYPE
        OBJECTS { hwMplsTunnelIfName, hwMplsTunnelFrrConfigOper }
        STATUS obsolete
        DESCRIPTION
            "When the trap indicating that TE-Frr configuration of Tunnel is changed is sent, the cause for the change of TE-FRR configuration of Tunnel is displayed."
        ::= { hwMplsExtendTrap 3 }
        
        hwMplsGlobalObject OBJECT IDENTIFIER ::= { hwMplsExtendMib 3 }

        hwMplsGlobalWorkMode OBJECT-TYPE
            SYNTAX INTEGER
                {
                standard(1),
                nonstandard(2)
                }
            MAX-ACCESS read-only
            STATUS current
            DESCRIPTION
                "The work mode of DS-TE system, default mode is nonstandard.
                Options:
                1. standard(1)       -indicates work mode of DS-TE system is standard
                2. nonstandard(2)    -indicates work mode of DS-TE system is nonstandard"
            ::= { hwMplsGlobalObject 1 }

        hwMplsGlobalBcModel OBJECT-TYPE
            SYNTAX INTEGER
                {
                rdm(1),
                mam(2),
                extendMam(3)
                }
            MAX-ACCESS read-only
            STATUS current
            DESCRIPTION
                "Bandwidth Constraint Model currently used by this LSR.
                Options: 
                1. rdm(1)          -indicates that the bandwidth constraint model is RDM.
                2. mam(2)          -indicates that the bandwidth constraint model is MAM.   
                3. extendMam(3)    -indicates that the bandwidth constraint model is ExtendMam."
            ::= { hwMplsGlobalObject 2 }
        
        hwMplsLspStatistics OBJECT IDENTIFIER ::= { hwMplsExtendMib 4 }
        
        hwMplsLspStatisticsTable OBJECT-TYPE
            SYNTAX SEQUENCE OF HwMplsLspStatisticsEntry
            MAX-ACCESS not-accessible
            STATUS current
            DESCRIPTION
                "hwMplsLspStatisticsTable is used to display the number of ingress LSPs,  
                transit LSPs, or egress LSPs of specified types. The index of this table 
                is hwMplsLspStatisticsLspType."
            ::= { hwMplsLspStatistics 1 }
        
        hwMplsLspStatisticsEntry OBJECT-TYPE
            SYNTAX HwMplsLspStatisticsEntry
            MAX-ACCESS not-accessible
            STATUS current
            DESCRIPTION
                "hwMplsLspStatisticsTable is used to display the number of ingress LSPs,  
                transit LSPs, or egress LSPs of specified types. The index of this entry 
                is hwMplsLspStatisticsLspType."
            INDEX { hwMplsLspStatisticsLspType }
            ::= { hwMplsLspStatisticsTable 1 }
        
        HwMplsLspStatisticsEntry ::=
            SEQUENCE { 
                hwMplsLspStatisticsLspType
                    INTEGER,
                hwMplsLspStatisticsIngressLspCount
                    Unsigned32,
                hwMplsLspStatisticsTransitLspCount
                    Unsigned32,
                hwMplsLspStatisticsEgressLspCount
                    Unsigned32,
                hwMplsLspStatisticsTotalLspCount
                    Unsigned32
             }

        hwMplsLspStatisticsLspType OBJECT-TYPE
            SYNTAX INTEGER
                {
                staticLsp(1),
                staticCrLsp(2),
                ldpLsp(3),
                rsvpCrLsp(4),
                bgpLsp(5),
                asbrLsp(6),
                bgpIpv6Lsp(7),
                l3vpnIpv6Lsp(8)
                }
            MAX-ACCESS not-accessible
            STATUS current
            DESCRIPTION
                "This object indicates the LSP type.
                Options:                                                      
                1. staticLsp(1)   -indicates the static LSP.    
                2. staticCrLsp(2) -indicates the static CR-LSP.  
                3. ldpLsp(3)      -indicates the LDP LSP.      
                4. rsvpCrLsp(4)   -indicates the RSVP LSP.     
                5. bgpLsp(5)      -indicates the BGP LSP.       
                6. asbrLsp(6)     -indicates the ASBR LSP.     
                7. bgpIpv6Lsp(7)  -indicates the BGP IPv6 LSP.  
                8. l3vpnIpv6Lsp(8)-indicates the L3VPN IPv6 LSP.
                "
            ::= { hwMplsLspStatisticsEntry 1 }
        
        hwMplsLspStatisticsIngressLspCount OBJECT-TYPE
            SYNTAX Unsigned32
            MAX-ACCESS read-only
            STATUS current
            DESCRIPTION
                "This object indicates the number of ingress LSPs of a specified type."
            ::= { hwMplsLspStatisticsEntry 2 }
        
        hwMplsLspStatisticsTransitLspCount OBJECT-TYPE
            SYNTAX Unsigned32
            MAX-ACCESS read-only
            STATUS current
            DESCRIPTION
                "This object indicates the number of transit LSPs of a specified type."
            ::= { hwMplsLspStatisticsEntry 3 }
        
        hwMplsLspStatisticsEgressLspCount OBJECT-TYPE
            SYNTAX Unsigned32
            MAX-ACCESS read-only
            STATUS current
            DESCRIPTION
                "This object indicates the number of egress LSPs of a specified type."
            ::= { hwMplsLspStatisticsEntry 4 }
        
        hwMplsLspStatisticsTotalLspCount OBJECT-TYPE
            SYNTAX Unsigned32
            MAX-ACCESS read-only
            STATUS current
            DESCRIPTION
                "This object indicates the total number of the ingress LSPs, transit LSPs and egress LSP of specified types."
            ::= { hwMplsLspStatisticsEntry 5 }
        
        hwMplsExtendConformance OBJECT IDENTIFIER ::= { hwMplsExtendMib 6 }
        
        hwMplsExtendGroups OBJECT IDENTIFIER ::= { hwMplsExtendConformance 1 }
        
        hwMplsTunnelGroup OBJECT-GROUP
            OBJECTS { hwTunnelFrrRouteDBInnerLabel, hwTunnelFrrRouteDBBypassIfIndex, hwTunnelFrrARHopProtActual, hwTunnelFrrARHopProtDesired, hwTunnelFrrBypassProtIfIndex, 
                hwStaticLspOwner, hwMplsTunnelClassType, hwMplsTunnelSessionAttr, hwMplsTunnelFrrARHopTableIndex, hwMplsTunnelName, 
                hwMplsTunnelIfIndex, hwMplsTunnelPreBandwidth, hwMplsTunnelNextBandwidth, hwMplsTunnelFrrSwitchover, hwMplsTunnelFrrBandwidth, 
                hwMplsTunnelOperStatus, hwMplsTunnelAdminStatus, hwMplsTunnelBandwidth, hwMplsTeVpnMaxBandwidth, hwMplsTeVpnAllocatedBandwidth, 
                hwMplsTunnelFrrHoldingPrio, hwMplsTunnelFrrSetupPrio, hwMplsTunnelFrrBypassTableIndex, hwMplsTunnelLspType,hwMplsTunnelInterfaceName }
            STATUS current
            DESCRIPTION 
                "Indicate the atrributes of the tunnel."
            ::= { hwMplsExtendGroups 1 }
        
        hwStaticLspGroup OBJECT-GROUP
            OBJECTS { hwStaticLspName, hwStaticLspStatus, hwStaticLspTnlToken }
            STATUS current
            DESCRIPTION 
                "Indicate the atrributes of the static lsp."
            ::= { hwMplsExtendGroups 2 }
        
        hwMplsDsTeGroup OBJECT-GROUP
            OBJECTS { hwMplsTunnelCt0Bandwidth, hwMplsTunnelCt1Bandwidth, hwMplsTunnelCt2Bandwidth, hwMplsTunnelCt3Bandwidth, hwMplsTunnelCt4Bandwidth, 
                hwMplsTunnelCt5Bandwidth, hwMplsTunnelCt6Bandwidth, hwMplsTunnelCt7Bandwidth, hwStaticLspClassType, hwStaticLspBandwidth, 
                hwMplsTeClassClassType, hwMplsTeClassPriority, hwMplsTeClassDescription, hwMplsGlobalBcModel, hwMplsGlobalWorkMode, 
                hwMplsIfBc7Bandwidth, hwMplsIfBc6Bandwidth, hwMplsIfBc5Bandwidth, hwMplsIfBc4Bandwidth, hwMplsIfBc3Bandwidth, 
                hwMplsIfBc2Bandwidth, hwMplsIfBc1Bandwidth, hwMplsIfBc0Bandwidth, hwMplsIfMaxResvBandwidth }
            STATUS current
            DESCRIPTION 
                "Indicate the atrributes about DS-TE."
            ::= { hwMplsExtendGroups 3 }
        
        hwMplsLspStatisticsGroup OBJECT-GROUP
            OBJECTS { hwMplsLspStatisticsIngressLspCount, hwMplsLspStatisticsTransitLspCount, hwMplsLspStatisticsEgressLspCount, hwMplsLspStatisticsTotalLspCount }
            STATUS current
            DESCRIPTION 
                "Indicate LSP statistics."
            ::= { hwMplsExtendGroups 4 }

        hwMplsObsoleteGroup OBJECT-GROUP
        OBJECTS { hwMplsTunnelIfName, hwMplsTunnelFrrConfigOper }
        STATUS obsolete
        DESCRIPTION 
           "Indicate the OBSOLETE objects of MPLS."
        ::= { hwMplsExtendGroups 5 }

     hwMplsTrapGroup OBJECT-GROUP
        OBJECTS { hwMplsTunnelDownReason }
        STATUS current
        DESCRIPTION 
           "For mpls trap object."
        ::= { hwMplsExtendGroups 6 }
        
        hwMplsExtendCompliances OBJECT IDENTIFIER ::= { hwMplsExtendConformance 2 }

        
        hwExtendTrapGroup NOTIFICATION-GROUP
            NOTIFICATIONS { hwMplsTeFrrProtAval, hwMplsTeFrrProtNotAval, hwMplsStaticLspUp, hwMplsStaticLspDown, hwMplsStaticCRLspUp, 
                hwMplsStaticCRLspDown, hwMplsTeFrrSwitch, hwMplsTeFrrResume, hwMplsTunnelHSBSwitch, hwMplsTunnelHSBResume, 
                hwMplsTunnelOBSwitch, hwMplsTunnelOBResume, hwMplsTunnelChangeBw, hwMplsTunnelTpOamLossSD, hwMplsOamSDRecovery, 
                hwMplsOamLoss, hwMplsOamLossRecovery, hwMplsOamAis, hwMplsOamAisRecovery, hwMplsOamRdi, hwMplsOamRdiRecovery, 
                hwMplsOamMeg, hwMplsOamMegRecovery, hwMplsOamMep, hwMplsOamMepRecovery, hwMplsOamSF, hwMplsOamSFRecovery, 
                hwMplsOamPeriod, hwMplsOamPeriodRecovery, hwMplsOamLck, hwMplsOamLckRecovery, hwMplsOamExcess, hwMplsOamExcessRecovery, 
                hwMplsOamMisMatch, hwMplsOamMisMatchRecovery, hwMplsOamMisMerge, hwMplsOamMisMergeRecovery, hwMplsOamUnknown, hwMplsOamUnknownRecovery, 
                hwMplsOamBDI, hwMplsOamBDIRecovery, hwMplsOamFail, hwMplsOamFailRecovery, 
                hwMplsTunnelPrimaryUp, hwMplsTunnelPrimaryDown, hwMplsTunnelHotstandbyUp, hwMplsTunnelHotstandbyDown,
                hwMplsTunnelOrdinaryUp, hwMplsTunnelOrdinaryDown, hwMplsTunnelBesteffortUp, hwMplsTunnelBesteffortDown
            }
            STATUS current
            DESCRIPTION 
                "Indicate the traps."
            ::= { hwMplsExtendCompliances 1 }

        hwObsoleteTrapGroup NOTIFICATION-GROUP
        NOTIFICATIONS { hwMplsTunnelFrrConfigChange, hwMplsTunnelUp, hwMplsTunnelDown }
        STATUS obsolete
        DESCRIPTION 
             "Indicate the Obsolete traps."
        ::= { hwMplsExtendCompliances 2 }
    
       -- 1.3.6.1.4.1.2011.5.25.121.7
        hwMplsRingMib OBJECT IDENTIFIER ::= { hwMplsExtendMib 7 }
        
        -- 1.3.6.1.4.1.2011.5.25.121.7.1
        hwMplsRingTable OBJECT-TYPE
        SYNTAX SEQUENCE OF HwMplsRingEntry
        MAX-ACCESS not-accessible
        STATUS current
        DESCRIPTION
                "Indicates the table information of the MPLS ring."
            ::= { hwMplsRingMib 1 }
        
        -- 1.3.6.1.4.1.2011.5.25.121.7.1.1
        hwMplsRingEntry OBJECT-TYPE
            SYNTAX HwMplsRingEntry
            MAX-ACCESS not-accessible
            STATUS current
            DESCRIPTION
                "Indicates the table information of the MPLS ring."
            INDEX {hwMplsRingID}
            ::= { hwMplsRingTable 1 }

        
        HwMplsRingEntry ::=
            SEQUENCE { 
                hwMplsRingID
                    Unsigned32,
                hwMplsRingNodeID
                    Unsigned32,
                hwMplsRingName
                    OCTET STRING,
                hwMplsRingDirection
                    OCTET STRING,
                hwMplsRingSwitchReason
                    OCTET STRING
             }
             
        -- 1.3.6.1.4.1.2011.5.25.121.7.1.1.1
        hwMplsRingID OBJECT-TYPE
            SYNTAX Unsigned32
            MAX-ACCESS not-accessible
            STATUS current
            DESCRIPTION
                "Indicates the ID of the MPLS ring. "
            ::= { hwMplsRingEntry 1 }
            
        -- 1.3.6.1.4.1.2011.5.25.121.7.1.1.2
        hwMplsRingNodeID OBJECT-TYPE
            SYNTAX Unsigned32
            MAX-ACCESS read-only
            STATUS current
            DESCRIPTION
                "Indicates the ID of the current Node on the MPLS ring."
            ::= { hwMplsRingEntry 2 }
            
        hwMplsRingName OBJECT-TYPE
            SYNTAX OCTET STRING
            MAX-ACCESS read-only
            STATUS current
            DESCRIPTION
                "Indicates the name of MPLS ring."
            ::= { hwMplsRingEntry 3 }
            
        hwMplsRingDirection OBJECT-TYPE
            SYNTAX OCTET STRING
            MAX-ACCESS read-only
            STATUS current
            DESCRIPTION
                "Indicates the direction of the MPLS ring."
            ::= { hwMplsRingEntry 4 }
        
        hwMplsRingSwitchReason OBJECT-TYPE
            SYNTAX OCTET STRING
            MAX-ACCESS read-only
            STATUS current
            DESCRIPTION
                "Indicates the switch reason of the MPLS ring."
            ::= { hwMplsRingEntry 5 }
        
        
        
        -- 1.3.6.1.4.1.2011.5.25.121.7.2
        hwMplsRingTrap OBJECT IDENTIFIER ::= { hwMplsRingMib 2 }
        
         -- 1.3.6.1.4.1.2011.5.25.121.7.2.1
        hwMplsRingSwitch NOTIFICATION-TYPE
            OBJECTS { hwMplsRingNodeID, hwMplsRingName, hwMplsRingDirection, hwMplsRingSwitchReason}
            STATUS current
            DESCRIPTION 
                "
                The notification indicates that the MPLS ring switched.
                "
            ::= { hwMplsRingTrap 1 }
            
         -- 1.3.6.1.4.1.2011.5.25.121.7.2.2    
       hwMplsRingResume NOTIFICATION-TYPE
            OBJECTS { hwMplsRingNodeID, hwMplsRingName, hwMplsRingDirection }
            STATUS current
            DESCRIPTION 
                "
                The notification indicates that the MPLS ring resumed.
                "
            ::= { hwMplsRingTrap 2 }
    END

--
-- HUAWEI-MPLS-EXTEND-MIB.mib
--
